FME workspace testData.fmw

Parameters:
- SourceDataset_CITYGML = $(FME_MF_DIR)GEO5014_Alderaan_Energy_ADE.gml   # Source CityGML File(s)
- DestDataset_CITYGML = $(FME_MF_DIR)Alderaan_enriched.gml   # Destination CityGML Document

Readers:
- CITYGML_1: CITYGML from $(SourceDataset_CITYGML)

Writers:
- CITYGML_2: CITYGML to $(DestDataset_CITYGML)

MechanicalVentilation (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_has_heat_recovery xml_boolean, energy_recuperation_factor xml_real64, energy_recuperation_factor_units xml_buffer
    -> AttributeManager_15
PhotovoltaicThermalSystem (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, citygml_level_of_detail{} xml_buffer, energy_installed_on_boundary_surface_xlink_href xml_buffer, energy_installed_on_building_installation_xlink_href xml_buffer, energy_cell_type xml_char(15), energy_collector_type xml_char(22), energy_module_area xml_real64, energy_module_area_units xml_buffer, energy_aperture_area xml_real64, energy_aperture_area_units xml_buffer, energy_optical_efficiency xml_real64, energy_optical_efficiency_units xml_buffer, energy_linear_heat_loss_coefficient xml_real64, energy_quadratic_heat_loss_coefficient xml_real64
    -> AttributeManager_22
ThermalDistributionSystem (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_distribution_perimeter xml_char(16), energy_distributes{}.xlink_href xml_buffer, energy_is_circulation xml_boolean, energy_medium xml_char(5), energy_nominal_flow xml_real64, energy_nominal_flow_units xml_buffer, energy_return_temperature xml_real64, energy_return_temperature_units xml_buffer, energy_supply_temperature xml_real64, energy_supply_temperature_units xml_buffer, energy_thermal_losses_factor xml_real64, energy_thermal_losses_factor_units xml_buffer
    -> AttributeManager_28
ThermalOpening (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_area xml_real64, energy_area_units xml_buffer, energy_construction_xlink_href xml_buffer, energy_indoor_shading_energy_shading_type_energy_maximum_cover_ratio xml_real64, energy_indoor_shading_energy_shading_type_energy_maximum_cover_ratio_units xml_buffer, energy_indoor_shading_energy_shading_type_energy_name xml_buffer, energy_indoor_shading_energy_shading_type_energy_transmittance_energy_transmittance_energy_fraction xml_real64, energy_indoor_shading_energy_shading_type_energy_transmittance_energy_transmittance_energy_fraction_units xml_buffer, energy_indoor_shading_energy_shading_type_energy_transmittance_energy_transmittance_energy_wavelength_range xml_char(8), energy_outdoor_shading_energy_shading_type_energy_maximum_cover_ratio xml_real64, energy_outdoor_shading_energy_shading_type_energy_maximum_cover_ratio_units xml_buffer, energy_outdoor_shading_energy_shading_type_energy_name xml_buffer,
      energy_outdoor_shading_energy_shading_type_energy_transmittance_energy_transmittance_energy_fraction xml_real64, energy_outdoor_shading_energy_shading_type_energy_transmittance_energy_transmittance_energy_fraction_units xml_buffer, energy_outdoor_shading_energy_shading_type_energy_transmittance_energy_transmittance_energy_wavelength_range xml_char(8), energy_openable_ratio xml_real64, energy_openable_ratio_units xml_buffer, citygml_level_of_detail{} xml_buffer, energy_relates_to{}.xlink_href xml_buffer
    -> AttributeManager_5
AttributeManager_5
    ATTR_TABLE:
      SET_TO energy_openable_ratio = 0.5
      SET_TO energy_openable_ratio_units = ratio
    -> ThermalOpening (writer CITYGML_2)
ThermalOpening (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_area xml_real64, energy_area_units xml_buffer, energy_construction_xlink_href xml_buffer, energy_indoor_shading_energy_shading_type_energy_maximum_cover_ratio xml_real64, energy_indoor_shading_energy_shading_type_energy_maximum_cover_ratio_units xml_buffer, energy_indoor_shading_energy_shading_type_energy_name xml_buffer, energy_indoor_shading_energy_shading_type_energy_transmittance_energy_transmittance_energy_fraction xml_real64, energy_indoor_shading_energy_shading_type_energy_transmittance_energy_transmittance_energy_fraction_units xml_buffer, energy_indoor_shading_energy_shading_type_energy_transmittance_energy_transmittance_energy_wavelength_range xml_char(8), energy_outdoor_shading_energy_shading_type_energy_maximum_cover_ratio xml_real64, energy_outdoor_shading_energy_shading_type_energy_maximum_cover_ratio_units xml_buffer, energy_outdoor_shading_energy_shading_type_energy_name xml_buffer,
      energy_outdoor_shading_energy_shading_type_energy_transmittance_energy_transmittance_energy_fraction xml_real64, energy_outdoor_shading_energy_shading_type_energy_transmittance_energy_transmittance_energy_fraction_units xml_buffer, energy_outdoor_shading_energy_shading_type_energy_transmittance_energy_transmittance_energy_wavelength_range xml_char(8), energy_openable_ratio xml_real64, energy_openable_ratio_units xml_buffer, citygml_level_of_detail{} xml_buffer, energy_relates_to{}.xlink_href xml_buffer
CombinedHeatPower (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_technology_type xml_buffer, energy_thermal_efficiency xml_real64, energy_thermal_efficiency_units xml_buffer, energy_electrical_efficiency xml_real64, energy_electrical_efficiency_units xml_buffer
    -> AttributeManager_14
ElectricalAppliances (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_operation_schedule xml_xml, energy_operation_schedule_xlink_href xml_buffer, energy_heat_dissipation_energy_heat_exchange_type_energy_convective_fraction xml_real64, energy_heat_dissipation_energy_heat_exchange_type_energy_convective_fraction_units xml_buffer, energy_heat_dissipation_energy_heat_exchange_type_energy_latent_fraction xml_real64, energy_heat_dissipation_energy_heat_exchange_type_energy_latent_fraction_units xml_buffer, energy_heat_dissipation_energy_heat_exchange_type_energy_radiant_fraction xml_real64, energy_heat_dissipation_energy_heat_exchange_type_energy_radiant_fraction_units xml_buffer, energy_heat_dissipation_energy_heat_exchange_type_energy_total_value xml_real64, energy_heat_dissipation_energy_heat_exchange_type_energy_total_value_units xml_buffer, energy_electrical_power xml_real64, energy_electrical_power_units xml_buffer
    -> ElectricalAppliances (writer CITYGML_2)
ElectricalAppliances (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_operation_schedule xml_xml, energy_operation_schedule_xlink_href xml_buffer, energy_heat_dissipation_energy_heat_exchange_type_energy_convective_fraction xml_real64, energy_heat_dissipation_energy_heat_exchange_type_energy_convective_fraction_units xml_buffer, energy_heat_dissipation_energy_heat_exchange_type_energy_latent_fraction xml_real64, energy_heat_dissipation_energy_heat_exchange_type_energy_latent_fraction_units xml_buffer, energy_heat_dissipation_energy_heat_exchange_type_energy_radiant_fraction xml_real64, energy_heat_dissipation_energy_heat_exchange_type_energy_radiant_fraction_units xml_buffer, energy_heat_dissipation_energy_heat_exchange_type_energy_total_value xml_real64, energy_heat_dissipation_energy_heat_exchange_type_energy_total_value_units xml_buffer, energy_electrical_power xml_real64, energy_electrical_power_units xml_buffer
ElectricalResistance (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer
    -> AttributeManager_13
EnergyDemand (reader CITYGML_1)
    attributes: citygml_target_uri xml_buffer, citygml_feature_role xml_buffer, citygml_feature_role_attr_name xml_buffer, citygml_feature_role_attr_val xml_buffer, gml_description xml_buffer, gml_name xml_buffer, energy_energy_amount xml_xml, energy_energy_amount_xlink_href xml_buffer, energy_end_use xml_char(20), energy_maximum_load xml_real64, energy_maximum_load_units xml_buffer, energy_energy_carrier_type xml_buffer, energy_energy_carrier_type_codeSpace xml_buffer, energy_demanded_by{}.xlink_href xml_buffer
    -> Tester
Tester
    BOOL_OP = OR
    TEST_CLAUSE = TEST @Value(gml_id) != id_energy_demand_10
    TEST_MODE = TEST
    PASSED -> EnergyDemand (writer CITYGML_2)
    FAILED -> AttributeManager_31
EnergyDemand (writer CITYGML_2)
    attributes: citygml_target_uri xml_buffer, citygml_feature_role xml_buffer, citygml_feature_role_attr_name xml_buffer, citygml_feature_role_attr_val xml_buffer, gml_description xml_buffer, gml_name xml_buffer, energy_energy_amount xml_xml, energy_energy_amount_xlink_href xml_buffer, energy_end_use xml_char(20), energy_maximum_load xml_real64, energy_maximum_load_units xml_buffer, energy_energy_carrier_type xml_buffer, energy_energy_carrier_type_codeSpace xml_buffer, energy_demanded_by{}.xlink_href xml_buffer
Facilities (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_operation_schedule xml_xml, energy_operation_schedule_xlink_href xml_buffer, energy_heat_dissipation_energy_heat_exchange_type_energy_convective_fraction xml_real64, energy_heat_dissipation_energy_heat_exchange_type_energy_convective_fraction_units xml_buffer, energy_heat_dissipation_energy_heat_exchange_type_energy_latent_fraction xml_real64, energy_heat_dissipation_energy_heat_exchange_type_energy_latent_fraction_units xml_buffer, energy_heat_dissipation_energy_heat_exchange_type_energy_radiant_fraction xml_real64, energy_heat_dissipation_energy_heat_exchange_type_energy_radiant_fraction_units xml_buffer, energy_heat_dissipation_energy_heat_exchange_type_energy_total_value xml_real64, energy_heat_dissipation_energy_heat_exchange_type_energy_total_value_units xml_buffer
    -> AttributeManager_4
Gas (reader CITYGML_1)
    attributes: citygml_target_uri xml_buffer, citygml_feature_role xml_buffer, citygml_feature_role_attr_name xml_buffer, citygml_feature_role_attr_val xml_buffer, gml_description xml_buffer, gml_name xml_buffer, energy_image_texture_xlink_href xml_buffer, energy_is_ventilated xml_boolean, energy_r_value xml_real64, energy_r_value_units xml_buffer
    -> AttributeManager_11
GenericConversionSystem (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer
    -> AttributeManager_17
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, citygml_level_of_detail{} xml_buffer, citygml_opening{}.xlink_href xml_buffer
    -> GroundSurface (writer CITYGML_2)
GroundSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, citygml_level_of_detail{} xml_buffer, citygml_opening{}.xlink_href xml_buffer
HeatExchanger (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_network_id xml_buffer, energy_network_node_id xml_buffer, energy_primary_heat_supplier xml_buffer
    -> AttributeManager_19
HeatPump (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_heat_source xml_char(25), energy_cop_source_temperature xml_real64, energy_cop_source_temperature_units xml_buffer, energy_cop_operation_temperature xml_real64, energy_cop_operation_temperature_units xml_buffer
    -> AttributeManager_18
Household (reader CITYGML_1)
    attributes: citygml_target_uri xml_buffer, citygml_feature_role xml_buffer, citygml_feature_role_attr_name xml_buffer, citygml_feature_role_attr_val xml_buffer, gml_description xml_buffer, gml_name xml_buffer, energy_residence_type xml_char(18), energy_household_type xml_char(15)
    -> Household (writer CITYGML_2)
Household (writer CITYGML_2)
    attributes: citygml_target_uri xml_buffer, citygml_feature_role xml_buffer, citygml_feature_role_attr_name xml_buffer, citygml_feature_role_attr_val xml_buffer, gml_description xml_buffer, gml_name xml_buffer, energy_residence_type xml_char(18), energy_household_type xml_char(15)
ImageTexture (reader CITYGML_1)
    attributes: citygml_target_uri xml_buffer, citygml_feature_role xml_buffer, citygml_feature_role_attr_name xml_buffer, citygml_feature_role_attr_val xml_buffer, gml_description xml_buffer, gml_name xml_buffer, energy_url xml_buffer, energy_repeat_s xml_boolean, energy_repeat_t xml_boolean
    -> AttributeManager_33
Layer (reader CITYGML_1)
    attributes: citygml_target_uri xml_buffer, citygml_feature_role xml_buffer, citygml_feature_role_attr_name xml_buffer, citygml_feature_role_attr_val xml_buffer, gml_description xml_buffer, gml_name xml_buffer, energy_layer_component{}.xlink_href xml_buffer
    -> Layer (writer CITYGML_2)
Layer (writer CITYGML_2)
    attributes: citygml_target_uri xml_buffer, citygml_feature_role xml_buffer, citygml_feature_role_attr_name xml_buffer, citygml_feature_role_attr_val xml_buffer, gml_description xml_buffer, gml_name xml_buffer, energy_layer_component{}.xlink_href xml_buffer
LayerComponent (reader CITYGML_1)
    attributes: citygml_target_uri xml_buffer, citygml_feature_role xml_buffer, citygml_feature_role_attr_name xml_buffer, citygml_feature_role_attr_val xml_buffer, energy_area_fraction xml_real64, energy_area_fraction_units xml_buffer, energy_thickness xml_real64, energy_thickness_units xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64, energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_material_xlink_href xml_buffer
    -> AttributeManager_10
LightingFacilities (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_operation_schedule xml_xml, energy_operation_schedule_xlink_href xml_buffer, energy_heat_dissipation_energy_heat_exchange_type_energy_convective_fraction xml_real64, energy_heat_dissipation_energy_heat_exchange_type_energy_convective_fraction_units xml_buffer, energy_heat_dissipation_energy_heat_exchange_type_energy_latent_fraction xml_real64, energy_heat_dissipation_energy_heat_exchange_type_energy_latent_fraction_units xml_buffer, energy_heat_dissipation_energy_heat_exchange_type_energy_radiant_fraction xml_real64, energy_heat_dissipation_energy_heat_exchange_type_energy_radiant_fraction_units xml_buffer, energy_heat_dissipation_energy_heat_exchange_type_energy_total_value xml_real64, energy_heat_dissipation_energy_heat_exchange_type_energy_total_value_units xml_buffer, energy_electrical_power xml_real64, energy_electrical_power_units xml_buffer
    -> LightingFacilities (writer CITYGML_2)
LightingFacilities (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_operation_schedule xml_xml, energy_operation_schedule_xlink_href xml_buffer, energy_heat_dissipation_energy_heat_exchange_type_energy_convective_fraction xml_real64, energy_heat_dissipation_energy_heat_exchange_type_energy_convective_fraction_units xml_buffer, energy_heat_dissipation_energy_heat_exchange_type_energy_latent_fraction xml_real64, energy_heat_dissipation_energy_heat_exchange_type_energy_latent_fraction_units xml_buffer, energy_heat_dissipation_energy_heat_exchange_type_energy_radiant_fraction xml_real64, energy_heat_dissipation_energy_heat_exchange_type_energy_radiant_fraction_units xml_buffer, energy_heat_dissipation_energy_heat_exchange_type_energy_total_value xml_real64, energy_heat_dissipation_energy_heat_exchange_type_energy_total_value_units xml_buffer, energy_electrical_power xml_real64, energy_electrical_power_units xml_buffer
Occupants (reader CITYGML_1)
    attributes: citygml_target_uri xml_buffer, citygml_feature_role xml_buffer, citygml_feature_role_attr_name xml_buffer, citygml_feature_role_attr_val xml_buffer, gml_description xml_buffer, gml_name xml_buffer, energy_heat_dissipation_energy_heat_exchange_type_energy_convective_fraction xml_real64, energy_heat_dissipation_energy_heat_exchange_type_energy_convective_fraction_units xml_buffer, energy_heat_dissipation_energy_heat_exchange_type_energy_latent_fraction xml_real64, energy_heat_dissipation_energy_heat_exchange_type_energy_latent_fraction_units xml_buffer, energy_heat_dissipation_energy_heat_exchange_type_energy_radiant_fraction xml_real64, energy_heat_dissipation_energy_heat_exchange_type_energy_radiant_fraction_units xml_buffer, energy_heat_dissipation_energy_heat_exchange_type_energy_total_value xml_real64, energy_heat_dissipation_energy_heat_exchange_type_energy_total_value_units xml_buffer, energy_number_of_occupants xml_int32, energy_occupancy_rate xml_xml, energy_occupancy_rate_xlink_href xml_buffer, energy_occupant_type xml_buffer, energy_occupant_type_codeSpace xml_buffer, energy_household{}.xlink_href xml_buffer
    -> AttributeManager_32
AttributeManager_32
    -> Occupants (writer CITYGML_2)
Occupants (writer CITYGML_2)
    attributes: citygml_target_uri xml_buffer, citygml_feature_role xml_buffer, citygml_feature_role_attr_name xml_buffer, citygml_feature_role_attr_val xml_buffer, gml_description xml_buffer, gml_name xml_buffer, energy_heat_dissipation_energy_heat_exchange_type_energy_convective_fraction xml_real64, energy_heat_dissipation_energy_heat_exchange_type_energy_convective_fraction_units xml_buffer, energy_heat_dissipation_energy_heat_exchange_type_energy_latent_fraction xml_real64, energy_heat_dissipation_energy_heat_exchange_type_energy_latent_fraction_units xml_buffer, energy_heat_dissipation_energy_heat_exchange_type_energy_radiant_fraction xml_real64, energy_heat_dissipation_energy_heat_exchange_type_energy_radiant_fraction_units xml_buffer, energy_heat_dissipation_energy_heat_exchange_type_energy_total_value xml_real64, energy_heat_dissipation_energy_heat_exchange_type_energy_total_value_units xml_buffer, energy_number_of_occupants xml_int32, energy_occupancy_rate xml_xml, energy_occupancy_rate_xlink_href xml_buffer, energy_occupant_type xml_buffer, energy_occupant_type_codeSpace xml_buffer, energy_household{}.xlink_href xml_buffer
PhotovoltaicSystem (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, citygml_level_of_detail{} xml_buffer, energy_installed_on_boundary_surface_xlink_href xml_buffer, energy_installed_on_building_installation_xlink_href xml_buffer, energy_cell_type xml_char(15), energy_module_area xml_real64, energy_module_area_units xml_buffer
    -> AttributeManager_21
PowerDistributionSystem (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_distribution_perimeter xml_char(16), energy_distributes{}.xlink_href xml_buffer, energy_current xml_real64, energy_current_units xml_buffer, energy_voltage xml_real64, energy_voltage_units xml_buffer
    -> AttributeManager_27
PowerStorageSystem (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_stores{}.xlink_href xml_buffer, energy_battery_technology xml_buffer, energy_power_capacity xml_real64, energy_power_capacity_units xml_buffer
    -> AttributeManager_26
ReverseConstruction (reader CITYGML_1)
    attributes: citygml_target_uri xml_buffer, citygml_feature_role xml_buffer, citygml_feature_role_attr_name xml_buffer, citygml_feature_role_attr_val xml_buffer, gml_description xml_buffer, gml_name xml_buffer, energy_base_construction_xlink_href xml_buffer
    -> AttributeManager_12
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, citygml_level_of_detail{} xml_buffer, citygml_opening{}.xlink_href xml_buffer
    -> RoofSurface (writer CITYGML_2)
RoofSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, citygml_level_of_detail{} xml_buffer, citygml_opening{}.xlink_href xml_buffer
SolarThermalSystem (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, citygml_level_of_detail{} xml_buffer, energy_installed_on_boundary_surface_xlink_href xml_buffer, energy_installed_on_building_installation_xlink_href xml_buffer, energy_collector_type xml_char(22), energy_aperture_area xml_real64, energy_aperture_area_units xml_buffer, energy_eta0 xml_real64, energy_a1 xml_real64, energy_a2 xml_real64
    -> AttributeManager_23
SolidMaterial (reader CITYGML_1)
    attributes: citygml_target_uri xml_buffer, citygml_feature_role xml_buffer, citygml_feature_role_attr_name xml_buffer, citygml_feature_role_attr_val xml_buffer, gml_description xml_buffer, gml_name xml_buffer, energy_image_texture_xlink_href xml_buffer, energy_conductivity xml_real64, energy_conductivity_units xml_buffer, energy_density xml_real64, energy_density_units xml_buffer, energy_permeance xml_real64, energy_permeance_units xml_buffer, energy_porosity xml_real64, energy_porosity_units xml_buffer, energy_specific_heat xml_real64, energy_specific_heat_units xml_buffer, energy_embodied_carbon xml_real64, energy_embodied_carbon_units xml_buffer, energy_embodied_energy xml_real64, energy_embodied_energy_units xml_buffer
    -> AttributeManager_2
AttributeManager_2
    ATTR_TABLE:
      SET_TO energy_embodied_carbon = 500
      SET_TO energy_embodied_carbon_units =  kg CO2/t
      SET_TO energy_embodied_energy = 1.2
      SET_TO energy_embodied_energy_units = MJ/kg
    -> SolidMaterial (writer CITYGML_2)
SolidMaterial (writer CITYGML_2)
    attributes: citygml_target_uri xml_buffer, citygml_feature_role xml_buffer, citygml_feature_role_attr_name xml_buffer, citygml_feature_role_attr_val xml_buffer, gml_description xml_buffer, gml_name xml_buffer, energy_image_texture_xlink_href xml_buffer, energy_conductivity xml_real64, energy_conductivity_units xml_buffer, energy_density xml_real64, energy_density_units xml_buffer, energy_permeance xml_real64, energy_permeance_units xml_buffer, energy_porosity xml_real64, energy_porosity_units xml_buffer, energy_specific_heat xml_real64, energy_specific_heat_units xml_buffer, energy_embodied_carbon xml_real64, energy_embodied_carbon_units xml_buffer, energy_embodied_energy xml_real64, energy_embodied_energy_units xml_buffer
SystemOperation (reader CITYGML_1)
    attributes: citygml_target_uri xml_buffer, citygml_feature_role xml_buffer, citygml_feature_role_attr_name xml_buffer, citygml_feature_role_attr_val xml_buffer, gml_description xml_buffer, gml_name xml_buffer, energy_end_use xml_char(20), energy_operation_time xml_xml, energy_operation_time_xlink_href xml_buffer, energy_yearly_global_efficiency xml_real64
    -> AttributeFilter_2
ThermalBoundary (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_thermal_boundary_type xml_char(17), energy_azimuth xml_real64, energy_azimuth_units xml_buffer, energy_inclination xml_real64, energy_inclination_units xml_buffer, energy_area xml_real64, energy_area_units xml_buffer, citygml_level_of_detail{} xml_buffer, energy_refurbishment_measure{}.energy_refurbishment_measure_energy_date_energy_date_of_event_energy_instant xml_buffer, energy_refurbishment_measure{}.energy_refurbishment_measure_energy_date_energy_date_of_event_energy_instant_frame xml_buffer, energy_refurbishment_measure{}.energy_refurbishment_measure_energy_date_energy_date_of_event_energy_instant_calendarEraName xml_buffer, energy_refurbishment_measure{}.energy_refurbishment_measure_energy_date_energy_date_of_event_energy_instant_indeterminatePosition xml_char(7), energy_refurbishment_measure{}.energy_refurbishment_measure_energy_date_energy_date_of_event_energy_period_xlink_href xml_buffer, energy_refurbishment_measure{}.energy_refurbishment_measure_energy_date_energy_date_of_event_energy_period_gml_time_period_frame xml_buffer,
      energy_refurbishment_measure{}.energy_refurbishment_measure_energy_date_energy_date_of_event_energy_period_gml_time_period_gml_id xml_buffer, energy_refurbishment_measure{}.energy_refurbishment_measure_energy_date_energy_date_of_event_energy_period_gml_time_period_gml_related_time{}.relativePosition xml_char(12), energy_refurbishment_measure{}.energy_refurbishment_measure_energy_date_energy_date_of_event_energy_period_gml_time_period_gml_related_time{}.xlink_href xml_buffer, energy_refurbishment_measure{}.energy_refurbishment_measure_energy_date_energy_date_of_event_energy_period_gml_time_period_gml_related_time{}.gml_time_edge_gml_id xml_buffer, energy_refurbishment_measure{}.energy_refurbishment_measure_energy_date_energy_date_of_event_energy_period_gml_time_period_gml_related_time{}.gml_time_edge_gml_related_time{} xml_xml, energy_refurbishment_measure{}.energy_refurbishment_measure_energy_date_energy_date_of_event_energy_period_gml_time_period_gml_related_time{}.gml_time_edge_gml_related_time{}.relativePosition xml_char(12), energy_refurbishment_measure{}.energy_refurbishment_measure_energy_date_energy_date_of_event_energy_period_gml_time_period_gml_related_time{}.gml_time_edge_gml_related_time{}.xlink_href xml_buffer, energy_refurbishment_measure{}.energy_refurbishment_measure_energy_date_energy_date_of_event_energy_period_gml_time_period_gml_related_time{}.gml_time_edge_gml_complex_xlink_href xml_buffer, energy_refurbishment_measure{}.energy_refurbishment_measure_energy_date_energy_date_of_event_energy_period_gml_time_period_gml_related_time{}.gml_time_edge_gml_start_xlink_href xml_buffer, energy_refurbishment_measure{}.energy_refurbishment_measure_energy_date_energy_date_of_event_energy_period_gml_time_period_gml_related_time{}.gml_time_edge_gml_start_gml_time_node_gml_id xml_buffer, energy_refurbishment_measure{}.energy_refurbishment_measure_energy_date_energy_date_of_event_energy_period_gml_time_period_gml_related_time{}.gml_time_edge_gml_start_gml_time_node_gml_related_time{} xml_xml, energy_refurbishment_measure{}.energy_refurbishment_measure_energy_date_energy_date_of_event_energy_period_gml_time_period_gml_related_time{}.gml_time_edge_gml_start_gml_time_node_gml_related_time{}.relativePosition xml_char(12), energy_refurbishment_measure{}.energy_refurbishment_measure_energy_date_energy_date_of_event_energy_period_gml_time_period_gml_related_time{}.gml_time_edge_gml_start_gml_time_node_gml_related_time{}.xlink_href xml_buffer, energy_refurbishment_measure{}.energy_refurbishment_measure_energy_date_energy_date_of_event_energy_period_gml_time_period_gml_related_time{}.gml_time_edge_gml_start_gml_time_node_gml_complex_xlink_href xml_buffer, energy_refurbishment_measure{}.energy_refurbishment_measure_energy_date_energy_date_of_event_energy_period_gml_time_period_gml_related_time{}.gml_time_edge_gml_start_gml_time_node_gml_previous_edge{}.xlink_href xml_buffer, energy_refurbishment_measure{}.energy_refurbishment_measure_energy_date_energy_date_of_event_energy_period_gml_time_period_gml_related_time{}.gml_time_edge_gml_start_gml_time_node_gml_previous_edge{}.gml_time_edge xml_xml, energy_refurbishment_measure{}.energy_refurbishment_measure_energy_date_energy_date_of_event_energy_period_gml_time_period_gml_related_time{}.gml_time_edge_gml_start_gml_time_node_gml_previous_edge{}.gml_time_edge_gml_id xml_buffer, energy_refurbishment_measure{}.energy_refurbishment_measure_energy_date_energy_date_of_event_energy_period_gml_time_period_gml_related_time{}.gml_time_edge_gml_start_gml_time_node_gml_next_edge{}.xlink_href xml_buffer, energy_refurbishment_measure{}.energy_refurbishment_measure_energy_date_energy_date_of_event_energy_period_gml_time_period_gml_related_time{}.gml_time_edge_gml_start_gml_time_node_gml_next_edge{}.gml_time_edge xml_xml, energy_refurbishment_measure{}.energy_refurbishment_measure_energy_date_energy_date_of_event_energy_period_gml_time_period_gml_related_time{}.gml_time_edge_gml_start_gml_time_node_gml_next_edge{}.gml_time_edge_gml_id xml_buffer, energy_refurbishment_measure{}.energy_refurbishment_measure_energy_date_energy_date_of_event_energy_period_gml_time_period_gml_related_time{}.gml_time_edge_gml_start_gml_time_node_gml_position_xlink_href xml_buffer, energy_refurbishment_measure{}.energy_refurbishment_measure_energy_date_energy_date_of_event_energy_period_gml_time_period_gml_related_time{}.gml_time_edge_gml_start_gml_time_node_gml_position_gml_time_instant_frame xml_buffer, energy_refurbishment_measure{}.energy_refurbishment_measure_energy_date_energy_date_of_event_energy_period_gml_time_period_gml_related_time{}.gml_time_edge_gml_start_gml_time_node_gml_position_gml_time_instant_gml_id xml_buffer, energy_refurbishment_measure{}.energy_refurbishment_measure_energy_date_energy_date_of_event_energy_period_gml_time_period_gml_related_time{}.gml_time_edge_gml_start_gml_time_node_gml_position_gml_time_instant_gml_related_time{} xml_xml, energy_refurbishment_measure{}.energy_refurbishment_measure_energy_date_energy_date_of_event_energy_period_gml_time_period_gml_related_time{}.gml_time_edge_gml_start_gml_time_node_gml_position_gml_time_instant_gml_related_time{}.relativePosition xml_char(12), energy_refurbishment_measure{}.energy_refurbishment_measure_energy_date_energy_date_of_event_energy_period_gml_time_period_gml_related_time{}.gml_time_edge_gml_start_gml_time_node_gml_position_gml_time_instant_gml_related_time{}.xlink_href xml_buffer, energy_refurbishment_measure{}.energy_refurbishment_measure_energy_date_energy_date_of_event_energy_period_gml_time_period_gml_related_time{}.gml_time_edge_gml_start_gml_time_node_gml_position_gml_time_instant_gml_time_position xml_buffer, energy_refurbishment_measure{}.energy_refurbishment_measure_energy_date_energy_date_of_event_energy_period_gml_time_period_gml_related_time{}.gml_time_edge_gml_start_gml_time_node_gml_position_gml_time_instant_gml_time_position_frame xml_buffer, energy_refurbishment_measure{}.energy_refurbishment_measure_energy_date_energy_date_of_event_energy_period_gml_time_period_gml_related_time{}.gml_time_edge_gml_start_gml_time_node_gml_position_gml_time_instant_gml_time_position_calendarEraName xml_buffer, energy_refurbishment_measure{}.energy_refurbishment_measure_energy_date_energy_date_of_event_energy_period_gml_time_period_gml_related_time{}.gml_time_edge_gml_start_gml_time_node_gml_position_gml_time_instant_gml_time_position_indeterminatePosition xml_char(7),
      energy_refurbishment_measure{}.energy_refurbishment_measure_energy_date_energy_date_of_event_energy_period_gml_time_period_gml_related_time{}.gml_time_edge_gml_end_xlink_href xml_buffer, energy_refurbishment_measure{}.energy_refurbishment_measure_energy_date_energy_date_of_event_energy_period_gml_time_period_gml_related_time{}.gml_time_edge_gml_end_gml_time_node_gml_id xml_buffer, energy_refurbishment_measure{}.energy_refurbishment_measure_energy_date_energy_date_of_event_energy_period_gml_time_period_gml_related_time{}.gml_time_edge_gml_end_gml_time_node_gml_related_time{} xml_xml, energy_refurbishment_measure{}.energy_refurbishment_measure_energy_date_energy_date_of_event_energy_period_gml_time_period_gml_related_time{}.gml_time_edge_gml_end_gml_time_node_gml_related_time{}.relativePosition xml_char(12), energy_refurbishment_measure{}.energy_refurbishment_measure_energy_date_energy_date_of_event_energy_period_gml_time_period_gml_related_time{}.gml_time_edge_gml_end_gml_time_node_gml_related_time{}.xlink_href xml_buffer, energy_refurbishment_measure{}.energy_refurbishment_measure_energy_date_energy_date_of_event_energy_period_gml_time_period_gml_related_time{}.gml_time_edge_gml_end_gml_time_node_gml_complex_xlink_href xml_buffer, energy_refurbishment_measure{}.energy_refurbishment_measure_energy_date_energy_date_of_event_energy_period_gml_time_period_gml_related_time{}.gml_time_edge_gml_end_gml_time_node_gml_previous_edge{}.xlink_href xml_buffer, energy_refurbishment_measure{}.energy_refurbishment_measure_energy_date_energy_date_of_event_energy_period_gml_time_period_gml_related_time{}.gml_time_edge_gml_end_gml_time_node_gml_previous_edge{}.gml_time_edge xml_xml, energy_refurbishment_measure{}.energy_refurbishment_measure_energy_date_energy_date_of_event_energy_period_gml_time_period_gml_related_time{}.gml_time_edge_gml_end_gml_time_node_gml_previous_edge{}.gml_time_edge_gml_id xml_buffer, energy_refurbishment_measure{}.energy_refurbishment_measure_energy_date_energy_date_of_event_energy_period_gml_time_period_gml_related_time{}.gml_time_edge_gml_end_gml_time_node_gml_next_edge{}.xlink_href xml_buffer, energy_refurbishment_measure{}.energy_refurbishment_measure_energy_date_energy_date_of_event_energy_period_gml_time_period_gml_related_time{}.gml_time_edge_gml_end_gml_time_node_gml_next_edge{}.gml_time_edge xml_xml, energy_refurbishment_measure{}.energy_refurbishment_measure_energy_date_energy_date_of_event_energy_period_gml_time_period_gml_related_time{}.gml_time_edge_gml_end_gml_time_node_gml_next_edge{}.gml_time_edge_gml_id xml_buffer, energy_refurbishment_measure{}.energy_refurbishment_measure_energy_date_energy_date_of_event_energy_period_gml_time_period_gml_related_time{}.gml_time_edge_gml_end_gml_time_node_gml_position_xlink_href xml_buffer, energy_refurbishment_measure{}.energy_refurbishment_measure_energy_date_energy_date_of_event_energy_period_gml_time_period_gml_related_time{}.gml_time_edge_gml_end_gml_time_node_gml_position_gml_time_instant_frame xml_buffer, energy_refurbishment_measure{}.energy_refurbishment_measure_energy_date_energy_date_of_event_energy_period_gml_time_period_gml_related_time{}.gml_time_edge_gml_end_gml_time_node_gml_position_gml_time_instant_gml_id xml_buffer, energy_refurbishment_measure{}.energy_refurbishment_measure_energy_date_energy_date_of_event_energy_period_gml_time_period_gml_related_time{}.gml_time_edge_gml_end_gml_time_node_gml_position_gml_time_instant_gml_related_time{} xml_xml, energy_refurbishment_measure{}.energy_refurbishment_measure_energy_date_energy_date_of_event_energy_period_gml_time_period_gml_related_time{}.gml_time_edge_gml_end_gml_time_node_gml_position_gml_time_instant_gml_related_time{}.relativePosition xml_char(12), energy_refurbishment_measure{}.energy_refurbishment_measure_energy_date_energy_date_of_event_energy_period_gml_time_period_gml_related_time{}.gml_time_edge_gml_end_gml_time_node_gml_position_gml_time_instant_gml_related_time{}.xlink_href xml_buffer, energy_refurbishment_measure{}.energy_refurbishment_measure_energy_date_energy_date_of_event_energy_period_gml_time_period_gml_related_time{}.gml_time_edge_gml_end_gml_time_node_gml_position_gml_time_instant_gml_time_position xml_buffer, energy_refurbishment_measure{}.energy_refurbishment_measure_energy_date_energy_date_of_event_energy_period_gml_time_period_gml_related_time{}.gml_time_edge_gml_end_gml_time_node_gml_position_gml_time_instant_gml_time_position_frame xml_buffer, energy_refurbishment_measure{}.energy_refurbishment_measure_energy_date_energy_date_of_event_energy_period_gml_time_period_gml_related_time{}.gml_time_edge_gml_end_gml_time_node_gml_position_gml_time_instant_gml_time_position_calendarEraName xml_buffer, energy_refurbishment_measure{}.energy_refurbishment_measure_energy_date_energy_date_of_event_energy_period_gml_time_period_gml_related_time{}.gml_time_edge_gml_end_gml_time_node_gml_position_gml_time_instant_gml_time_position_indeterminatePosition xml_char(7), energy_refurbishment_measure{}.energy_refurbishment_measure_energy_date_energy_date_of_event_energy_period_gml_time_period_gml_related_time{}.gml_time_edge_gml_extent_xlink_href xml_buffer, energy_refurbishment_measure{}.energy_refurbishment_measure_energy_date_energy_date_of_event_energy_period_gml_time_period_gml_related_time{}.gml_time_edge_gml_extent_gml_time_period xml_xml, energy_refurbishment_measure{}.energy_refurbishment_measure_energy_date_energy_date_of_event_energy_period_gml_time_period_gml_related_time{}.gml_time_edge_gml_extent_gml_time_period_frame xml_buffer, energy_refurbishment_measure{}.energy_refurbishment_measure_energy_date_energy_date_of_event_energy_period_gml_time_period_gml_related_time{}.gml_time_edge_gml_extent_gml_time_period_gml_id xml_buffer, energy_refurbishment_measure{}.energy_refurbishment_measure_energy_date_energy_date_of_event_energy_period_gml_time_period_gml_related_time{}.gml_time_instant_frame xml_buffer, energy_refurbishment_measure{}.energy_refurbishment_measure_energy_date_energy_date_of_event_energy_period_gml_time_period_gml_related_time{}.gml_time_instant_gml_id xml_buffer, energy_refurbishment_measure{}.energy_refurbishment_measure_energy_date_energy_date_of_event_energy_period_gml_time_period_gml_related_time{}.gml_time_instant_gml_related_time{} xml_xml, energy_refurbishment_measure{}.energy_refurbishment_measure_energy_date_energy_date_of_event_energy_period_gml_time_period_gml_related_time{}.gml_time_instant_gml_related_time{}.relativePosition xml_char(12),
      energy_refurbishment_measure{}.energy_refurbishment_measure_energy_date_energy_date_of_event_energy_period_gml_time_period_gml_related_time{}.gml_time_instant_gml_related_time{}.xlink_href xml_buffer, energy_refurbishment_measure{}.energy_refurbishment_measure_energy_date_energy_date_of_event_energy_period_gml_time_period_gml_related_time{}.gml_time_instant_gml_time_position xml_buffer, energy_refurbishment_measure{}.energy_refurbishment_measure_energy_date_energy_date_of_event_energy_period_gml_time_period_gml_related_time{}.gml_time_instant_gml_time_position_frame xml_buffer, energy_refurbishment_measure{}.energy_refurbishment_measure_energy_date_energy_date_of_event_energy_period_gml_time_period_gml_related_time{}.gml_time_instant_gml_time_position_calendarEraName xml_buffer, energy_refurbishment_measure{}.energy_refurbishment_measure_energy_date_energy_date_of_event_energy_period_gml_time_period_gml_related_time{}.gml_time_instant_gml_time_position_indeterminatePosition xml_char(7), energy_refurbishment_measure{}.energy_refurbishment_measure_energy_date_energy_date_of_event_energy_period_gml_time_period_gml_related_time{}.gml_time_node_gml_id xml_buffer, energy_refurbishment_measure{}.energy_refurbishment_measure_energy_date_energy_date_of_event_energy_period_gml_time_period_gml_related_time{}.gml_time_node_gml_related_time{} xml_xml, energy_refurbishment_measure{}.energy_refurbishment_measure_energy_date_energy_date_of_event_energy_period_gml_time_period_gml_related_time{}.gml_time_node_gml_related_time{}.relativePosition xml_char(12), energy_refurbishment_measure{}.energy_refurbishment_measure_energy_date_energy_date_of_event_energy_period_gml_time_period_gml_related_time{}.gml_time_node_gml_related_time{}.xlink_href xml_buffer, energy_refurbishment_measure{}.energy_refurbishment_measure_energy_date_energy_date_of_event_energy_period_gml_time_period_gml_related_time{}.gml_time_node_gml_complex_xlink_href xml_buffer, energy_refurbishment_measure{}.energy_refurbishment_measure_energy_date_energy_date_of_event_energy_period_gml_time_period_gml_related_time{}.gml_time_node_gml_previous_edge{}.xlink_href xml_buffer, energy_refurbishment_measure{}.energy_refurbishment_measure_energy_date_energy_date_of_event_energy_period_gml_time_period_gml_related_time{}.gml_time_node_gml_previous_edge{}.gml_time_edge_gml_id xml_buffer, energy_refurbishment_measure{}.energy_refurbishment_measure_energy_date_energy_date_of_event_energy_period_gml_time_period_gml_related_time{}.gml_time_node_gml_previous_edge{}.gml_time_edge_gml_related_time{} xml_xml, energy_refurbishment_measure{}.energy_refurbishment_measure_energy_date_energy_date_of_event_energy_period_gml_time_period_gml_related_time{}.gml_time_node_gml_previous_edge{}.gml_time_edge_gml_related_time{}.relativePosition xml_char(12), energy_refurbishment_measure{}.energy_refurbishment_measure_energy_date_energy_date_of_event_energy_period_gml_time_period_gml_related_time{}.gml_time_node_gml_previous_edge{}.gml_time_edge_gml_related_time{}.xlink_href xml_buffer, energy_refurbishment_measure{}.energy_refurbishment_measure_energy_date_energy_date_of_event_energy_period_gml_time_period_gml_related_time{}.gml_time_node_gml_previous_edge{}.gml_time_edge_gml_complex_xlink_href xml_buffer, energy_refurbishment_measure{}.energy_refurbishment_measure_energy_date_energy_date_of_event_energy_period_gml_time_period_gml_related_time{}.gml_time_node_gml_previous_edge{}.gml_time_edge_gml_start_xlink_href xml_buffer, energy_refurbishment_measure{}.energy_refurbishment_measure_energy_date_energy_date_of_event_energy_period_gml_time_period_gml_related_time{}.gml_time_node_gml_previous_edge{}.gml_time_edge_gml_start_gml_time_node xml_xml, energy_refurbishment_measure{}.energy_refurbishment_measure_energy_date_energy_date_of_event_energy_period_gml_time_period_gml_related_time{}.gml_time_node_gml_previous_edge{}.gml_time_edge_gml_start_gml_time_node_gml_id xml_buffer, energy_refurbishment_measure{}.energy_refurbishment_measure_energy_date_energy_date_of_event_energy_period_gml_time_period_gml_related_time{}.gml_time_node_gml_previous_edge{}.gml_time_edge_gml_end_xlink_href xml_buffer, energy_refurbishment_measure{}.energy_refurbishment_measure_energy_date_energy_date_of_event_energy_period_gml_time_period_gml_related_time{}.gml_time_node_gml_previous_edge{}.gml_time_edge_gml_end_gml_time_node xml_xml, energy_refurbishment_measure{}.energy_refurbishment_measure_energy_date_energy_date_of_event_energy_period_gml_time_period_gml_related_time{}.gml_time_node_gml_previous_edge{}.gml_time_edge_gml_end_gml_time_node_gml_id xml_buffer, energy_refurbishment_measure{}.energy_refurbishment_measure_energy_date_energy_date_of_event_energy_period_gml_time_period_gml_related_time{}.gml_time_node_gml_previous_edge{}.gml_time_edge_gml_extent_xlink_href xml_buffer, energy_refurbishment_measure{}.energy_refurbishment_measure_energy_date_energy_date_of_event_energy_period_gml_time_period_gml_related_time{}.gml_time_node_gml_previous_edge{}.gml_time_edge_gml_extent_gml_time_period xml_xml, energy_refurbishment_measure{}.energy_refurbishment_measure_energy_date_energy_date_of_event_energy_period_gml_time_period_gml_related_time{}.gml_time_node_gml_previous_edge{}.gml_time_edge_gml_extent_gml_time_period_frame xml_buffer, energy_refurbishment_measure{}.energy_refurbishment_measure_energy_date_energy_date_of_event_energy_period_gml_time_period_gml_related_time{}.gml_time_node_gml_previous_edge{}.gml_time_edge_gml_extent_gml_time_period_gml_id xml_buffer, energy_refurbishment_measure{}.energy_refurbishment_measure_energy_date_energy_date_of_event_energy_period_gml_time_period_gml_related_time{}.gml_time_node_gml_next_edge{}.xlink_href xml_buffer, energy_refurbishment_measure{}.energy_refurbishment_measure_energy_date_energy_date_of_event_energy_period_gml_time_period_gml_related_time{}.gml_time_node_gml_next_edge{}.gml_time_edge_gml_id xml_buffer, energy_refurbishment_measure{}.energy_refurbishment_measure_energy_date_energy_date_of_event_energy_period_gml_time_period_gml_related_time{}.gml_time_node_gml_next_edge{}.gml_time_edge_gml_related_time{} xml_xml, energy_refurbishment_measure{}.energy_refurbishment_measure_energy_date_energy_date_of_event_energy_period_gml_time_period_gml_related_time{}.gml_time_node_gml_next_edge{}.gml_time_edge_gml_related_time{}.relativePosition xml_char(12),
      energy_refurbishment_measure{}.energy_refurbishment_measure_energy_date_energy_date_of_event_energy_period_gml_time_period_gml_related_time{}.gml_time_node_gml_next_edge{}.gml_time_edge_gml_related_time{}.xlink_href xml_buffer, energy_refurbishment_measure{}.energy_refurbishment_measure_energy_date_energy_date_of_event_energy_period_gml_time_period_gml_related_time{}.gml_time_node_gml_next_edge{}.gml_time_edge_gml_complex_xlink_href xml_buffer, energy_refurbishment_measure{}.energy_refurbishment_measure_energy_date_energy_date_of_event_energy_period_gml_time_period_gml_related_time{}.gml_time_node_gml_next_edge{}.gml_time_edge_gml_start_xlink_href xml_buffer, energy_refurbishment_measure{}.energy_refurbishment_measure_energy_date_energy_date_of_event_energy_period_gml_time_period_gml_related_time{}.gml_time_node_gml_next_edge{}.gml_time_edge_gml_start_gml_time_node xml_xml, energy_refurbishment_measure{}.energy_refurbishment_measure_energy_date_energy_date_of_event_energy_period_gml_time_period_gml_related_time{}.gml_time_node_gml_next_edge{}.gml_time_edge_gml_start_gml_time_node_gml_id xml_buffer, energy_refurbishment_measure{}.energy_refurbishment_measure_energy_date_energy_date_of_event_energy_period_gml_time_period_gml_related_time{}.gml_time_node_gml_next_edge{}.gml_time_edge_gml_end_xlink_href xml_buffer, energy_refurbishment_measure{}.energy_refurbishment_measure_energy_date_energy_date_of_event_energy_period_gml_time_period_gml_related_time{}.gml_time_node_gml_next_edge{}.gml_time_edge_gml_end_gml_time_node xml_xml, energy_refurbishment_measure{}.energy_refurbishment_measure_energy_date_energy_date_of_event_energy_period_gml_time_period_gml_related_time{}.gml_time_node_gml_next_edge{}.gml_time_edge_gml_end_gml_time_node_gml_id xml_buffer, energy_refurbishment_measure{}.energy_refurbishment_measure_energy_date_energy_date_of_event_energy_period_gml_time_period_gml_related_time{}.gml_time_node_gml_next_edge{}.gml_time_edge_gml_extent_xlink_href xml_buffer, energy_refurbishment_measure{}.energy_refurbishment_measure_energy_date_energy_date_of_event_energy_period_gml_time_period_gml_related_time{}.gml_time_node_gml_next_edge{}.gml_time_edge_gml_extent_gml_time_period xml_xml, energy_refurbishment_measure{}.energy_refurbishment_measure_energy_date_energy_date_of_event_energy_period_gml_time_period_gml_related_time{}.gml_time_node_gml_next_edge{}.gml_time_edge_gml_extent_gml_time_period_frame xml_buffer, energy_refurbishment_measure{}.energy_refurbishment_measure_energy_date_energy_date_of_event_energy_period_gml_time_period_gml_related_time{}.gml_time_node_gml_next_edge{}.gml_time_edge_gml_extent_gml_time_period_gml_id xml_buffer, energy_refurbishment_measure{}.energy_refurbishment_measure_energy_date_energy_date_of_event_energy_period_gml_time_period_gml_related_time{}.gml_time_node_gml_position_xlink_href xml_buffer, energy_refurbishment_measure{}.energy_refurbishment_measure_energy_date_energy_date_of_event_energy_period_gml_time_period_gml_related_time{}.gml_time_node_gml_position_gml_time_instant_frame xml_buffer, energy_refurbishment_measure{}.energy_refurbishment_measure_energy_date_energy_date_of_event_energy_period_gml_time_period_gml_related_time{}.gml_time_node_gml_position_gml_time_instant_gml_id xml_buffer, energy_refurbishment_measure{}.energy_refurbishment_measure_energy_date_energy_date_of_event_energy_period_gml_time_period_gml_related_time{}.gml_time_node_gml_position_gml_time_instant_gml_related_time{} xml_xml, energy_refurbishment_measure{}.energy_refurbishment_measure_energy_date_energy_date_of_event_energy_period_gml_time_period_gml_related_time{}.gml_time_node_gml_position_gml_time_instant_gml_related_time{}.relativePosition xml_char(12), energy_refurbishment_measure{}.energy_refurbishment_measure_energy_date_energy_date_of_event_energy_period_gml_time_period_gml_related_time{}.gml_time_node_gml_position_gml_time_instant_gml_related_time{}.xlink_href xml_buffer, energy_refurbishment_measure{}.energy_refurbishment_measure_energy_date_energy_date_of_event_energy_period_gml_time_period_gml_related_time{}.gml_time_node_gml_position_gml_time_instant_gml_time_position xml_buffer, energy_refurbishment_measure{}.energy_refurbishment_measure_energy_date_energy_date_of_event_energy_period_gml_time_period_gml_related_time{}.gml_time_node_gml_position_gml_time_instant_gml_time_position_frame xml_buffer, energy_refurbishment_measure{}.energy_refurbishment_measure_energy_date_energy_date_of_event_energy_period_gml_time_period_gml_related_time{}.gml_time_node_gml_position_gml_time_instant_gml_time_position_calendarEraName xml_buffer, energy_refurbishment_measure{}.energy_refurbishment_measure_energy_date_energy_date_of_event_energy_period_gml_time_period_gml_related_time{}.gml_time_node_gml_position_gml_time_instant_gml_time_position_indeterminatePosition xml_char(7), energy_refurbishment_measure{}.energy_refurbishment_measure_energy_date_energy_date_of_event_energy_period_gml_time_period_gml_related_time{}.gml_time_period xml_xml, energy_refurbishment_measure{}.energy_refurbishment_measure_energy_date_energy_date_of_event_energy_period_gml_time_period_gml_related_time{}.gml_time_period_frame xml_buffer, energy_refurbishment_measure{}.energy_refurbishment_measure_energy_date_energy_date_of_event_energy_period_gml_time_period_gml_related_time{}.gml_time_period_gml_id xml_buffer, energy_refurbishment_measure{}.energy_refurbishment_measure_energy_date_energy_date_of_event_energy_period_gml_time_period_gml_begin_position xml_buffer, energy_refurbishment_measure{}.energy_refurbishment_measure_energy_date_energy_date_of_event_energy_period_gml_time_period_gml_begin_position_frame xml_buffer, energy_refurbishment_measure{}.energy_refurbishment_measure_energy_date_energy_date_of_event_energy_period_gml_time_period_gml_begin_position_calendarEraName xml_buffer, energy_refurbishment_measure{}.energy_refurbishment_measure_energy_date_energy_date_of_event_energy_period_gml_time_period_gml_begin_position_indeterminatePosition xml_char(7), energy_refurbishment_measure{}.energy_refurbishment_measure_energy_date_energy_date_of_event_energy_period_gml_time_period_gml_begin_xlink_href xml_buffer,
      energy_refurbishment_measure{}.energy_refurbishment_measure_energy_date_energy_date_of_event_energy_period_gml_time_period_gml_begin_gml_time_instant_frame xml_buffer, energy_refurbishment_measure{}.energy_refurbishment_measure_energy_date_energy_date_of_event_energy_period_gml_time_period_gml_begin_gml_time_instant_gml_id xml_buffer, energy_refurbishment_measure{}.energy_refurbishment_measure_energy_date_energy_date_of_event_energy_period_gml_time_period_gml_begin_gml_time_instant_gml_related_time{}.relativePosition xml_char(12), energy_refurbishment_measure{}.energy_refurbishment_measure_energy_date_energy_date_of_event_energy_period_gml_time_period_gml_begin_gml_time_instant_gml_related_time{}.xlink_href xml_buffer, energy_refurbishment_measure{}.energy_refurbishment_measure_energy_date_energy_date_of_event_energy_period_gml_time_period_gml_begin_gml_time_instant_gml_related_time{}.gml_time_edge_gml_id xml_buffer, energy_refurbishment_measure{}.energy_refurbishment_measure_energy_date_energy_date_of_event_energy_period_gml_time_period_gml_begin_gml_time_instant_gml_related_time{}.gml_time_edge_gml_related_time{} xml_xml, energy_refurbishment_measure{}.energy_refurbishment_measure_energy_date_energy_date_of_event_energy_period_gml_time_period_gml_begin_gml_time_instant_gml_related_time{}.gml_time_edge_gml_related_time{}.relativePosition xml_char(12), energy_refurbishment_measure{}.energy_refurbishment_measure_energy_date_energy_date_of_event_energy_period_gml_time_period_gml_begin_gml_time_instant_gml_related_time{}.gml_time_edge_gml_related_time{}.xlink_href xml_buffer, energy_refurbishment_measure{}.energy_refurbishment_measure_energy_date_energy_date_of_event_energy_period_gml_time_period_gml_begin_gml_time_instant_gml_related_time{}.gml_time_edge_gml_complex_xlink_href xml_buffer, energy_refurbishment_measure{}.energy_refurbishment_measure_energy_date_energy_date_of_event_energy_period_gml_time_period_gml_begin_gml_time_instant_gml_related_time{}.gml_time_edge_gml_start_xlink_href xml_buffer, energy_refurbishment_measure{}.energy_refurbishment_measure_energy_date_energy_date_of_event_energy_period_gml_time_period_gml_begin_gml_time_instant_gml_related_time{}.gml_time_edge_gml_start_gml_time_node_gml_id xml_buffer, energy_refurbishment_measure{}.energy_refurbishment_measure_energy_date_energy_date_of_event_energy_period_gml_time_period_gml_begin_gml_time_instant_gml_related_time{}.gml_time_edge_gml_start_gml_time_node_gml_related_time{} xml_xml, energy_refurbishment_measure{}.energy_refurbishment_measure_energy_date_energy_date_of_event_energy_period_gml_time_period_gml_begin_gml_time_instant_gml_related_time{}.gml_time_edge_gml_start_gml_time_node_gml_related_time{}.relativePosition xml_char(12), energy_refurbishment_measure{}.energy_refurbishment_measure_energy_date_energy_date_of_event_energy_period_gml_time_period_gml_begin_gml_time_instant_gml_related_time{}.gml_time_edge_gml_start_gml_time_node_gml_related_time{}.xlink_href xml_buffer, energy_refurbishment_measure{}.energy_refurbishment_measure_energy_date_energy_date_of_event_energy_period_gml_time_period_gml_begin_gml_time_instant_gml_related_time{}.gml_time_edge_gml_start_gml_time_node_gml_complex_xlink_href xml_buffer, energy_refurbishment_measure{}.energy_refurbishment_measure_energy_date_energy_date_of_event_energy_period_gml_time_period_gml_begin_gml_time_instant_gml_related_time{}.gml_time_edge_gml_start_gml_time_node_gml_previous_edge{}.xlink_href xml_buffer, energy_refurbishment_measure{}.energy_refurbishment_measure_energy_date_energy_date_of_event_energy_period_gml_time_period_gml_begin_gml_time_instant_gml_related_time{}.gml_time_edge_gml_start_gml_time_node_gml_previous_edge{}.gml_time_edge xml_xml, energy_refurbishment_measure{}.energy_refurbishment_measure_energy_date_energy_date_of_event_energy_period_gml_time_period_gml_begin_gml_time_instant_gml_related_time{}.gml_time_edge_gml_start_gml_time_node_gml_previous_edge{}.gml_time_edge_gml_id xml_buffer, energy_refurbishment_measure{}.energy_refurbishment_measure_energy_date_energy_date_of_event_energy_period_gml_time_period_gml_begin_gml_time_instant_gml_related_time{}.gml_time_edge_gml_start_gml_time_node_gml_next_edge{}.xlink_href xml_buffer, energy_refurbishment_measure{}.energy_refurbishment_measure_energy_date_energy_date_of_event_energy_period_gml_time_period_gml_begin_gml_time_instant_gml_related_time{}.gml_time_edge_gml_start_gml_time_node_gml_next_edge{}.gml_time_edge xml_xml, energy_refurbishment_measure{}.energy_refurbishment_measure_energy_date_energy_date_of_event_energy_period_gml_time_period_gml_begin_gml_time_instant_gml_related_time{}.gml_time_edge_gml_start_gml_time_node_gml_next_edge{}.gml_time_edge_gml_id xml_buffer, energy_refurbishment_measure{}.energy_refurbishment_measure_energy_date_energy_date_of_event_energy_period_gml_time_period_gml_begin_gml_time_instant_gml_related_time{}.gml_time_edge_gml_start_gml_time_node_gml_position_xlink_href xml_buffer, energy_refurbishment_measure{}.energy_refurbishment_measure_energy_date_energy_date_of_event_energy_period_gml_time_period_gml_begin_gml_time_instant_gml_related_time{}.gml_time_edge_gml_start_gml_time_node_gml_position_gml_time_instant xml_xml, energy_refurbishment_measure{}.energy_refurbishment_measure_energy_date_energy_date_of_event_energy_period_gml_time_period_gml_begin_gml_time_instant_gml_related_time{}.gml_time_edge_gml_start_gml_time_node_gml_position_gml_time_instant_frame xml_buffer, energy_refurbishment_measure{}.energy_refurbishment_measure_energy_date_energy_date_of_event_energy_period_gml_time_period_gml_begin_gml_time_instant_gml_related_time{}.gml_time_edge_gml_start_gml_time_node_gml_position_gml_time_instant_gml_id xml_buffer, energy_refurbishment_measure{}.energy_refurbishment_measure_energy_date_energy_date_of_event_energy_period_gml_time_period_gml_begin_gml_time_instant_gml_related_time{}.gml_time_edge_gml_end_xlink_href xml_buffer, energy_refurbishment_measure{}.energy_refurbishment_measure_energy_date_energy_date_of_event_energy_period_gml_time_period_gml_begin_gml_time_instant_gml_related_time{}.gml_time_edge_gml_end_gml_time_node_gml_id xml_buffer, energy_refurbishment_measure{}.energy_refurbishment_measure_energy_date_energy_date_of_event_energy_period_gml_time_period_gml_begin_gml_time_instant_gml_related_time{}.gml_time_edge_gml_end_gml_time_node_gml_related_time{} xml_xml, energy_refurbishment_measure{}.energy_refurbishment_measure_energy_date_energy_date_of_event_energy_period_gml_time_period_gml_begin_gml_time_instant_gml_related_time{}.gml_time_edge_gml_end_gml_time_node_gml_related_time{}.relativePosition xml_char(12), energy_refurbishment_measure{}.energy_refurbishment_measure_energy_date_energy_date_of_event_energy_period_gml_time_period_gml_begin_gml_time_instant_gml_related_time{}.gml_time_edge_gml_end_gml_time_node_gml_related_time{}.xlink_href xml_buffer,
      energy_refurbishment_measure{}.energy_refurbishment_measure_energy_date_energy_date_of_event_energy_period_gml_time_period_gml_begin_gml_time_instant_gml_related_time{}.gml_time_edge_gml_end_gml_time_node_gml_complex_xlink_href xml_buffer, energy_refurbishment_measure{}.energy_refurbishment_measure_energy_date_energy_date_of_event_energy_period_gml_time_period_gml_begin_gml_time_instant_gml_related_time{}.gml_time_edge_gml_end_gml_time_node_gml_previous_edge{}.xlink_href xml_buffer, energy_refurbishment_measure{}.energy_refurbishment_measure_energy_date_energy_date_of_event_energy_period_gml_time_period_gml_begin_gml_time_instant_gml_related_time{}.gml_time_edge_gml_end_gml_time_node_gml_previous_edge{}.gml_time_edge xml_xml, energy_refurbishment_measure{}.energy_refurbishment_measure_energy_date_energy_date_of_event_energy_period_gml_time_period_gml_begin_gml_time_instant_gml_related_time{}.gml_time_edge_gml_end_gml_time_node_gml_previous_edge{}.gml_time_edge_gml_id xml_buffer, energy_refurbishment_measure{}.energy_refurbishment_measure_energy_date_energy_date_of_event_energy_period_gml_time_period_gml_begin_gml_time_instant_gml_related_time{}.gml_time_edge_gml_end_gml_time_node_gml_next_edge{}.xlink_href xml_buffer, energy_refurbishment_measure{}.energy_refurbishment_measure_energy_date_energy_date_of_event_energy_period_gml_time_period_gml_begin_gml_time_instant_gml_related_time{}.gml_time_edge_gml_end_gml_time_node_gml_next_edge{}.gml_time_edge xml_xml, energy_refurbishment_measure{}.energy_refurbishment_measure_energy_date_energy_date_of_event_energy_period_gml_time_period_gml_begin_gml_time_instant_gml_related_time{}.gml_time_edge_gml_end_gml_time_node_gml_next_edge{}.gml_time_edge_gml_id xml_buffer, energy_refurbishment_measure{}.energy_refurbishment_measure_energy_date_energy_date_of_event_energy_period_gml_time_period_gml_begin_gml_time_instant_gml_related_time{}.gml_time_edge_gml_end_gml_time_node_gml_position_xlink_href xml_buffer, energy_refurbishment_measure{}.energy_refurbishment_measure_energy_date_energy_date_of_event_energy_period_gml_time_period_gml_begin_gml_time_instant_gml_related_time{}.gml_time_edge_gml_end_gml_time_node_gml_position_gml_time_instant xml_xml, energy_refurbishment_measure{}.energy_refurbishment_measure_energy_date_energy_date_of_event_energy_period_gml_time_period_gml_begin_gml_time_instant_gml_related_time{}.gml_time_edge_gml_end_gml_time_node_gml_position_gml_time_instant_frame xml_buffer, energy_refurbishment_measure{}.energy_refurbishment_measure_energy_date_energy_date_of_event_energy_period_gml_time_period_gml_begin_gml_time_instant_gml_related_time{}.gml_time_edge_gml_end_gml_time_node_gml_position_gml_time_instant_gml_id xml_buffer, energy_refurbishment_measure{}.energy_refurbishment_measure_energy_date_energy_date_of_event_energy_period_gml_time_period_gml_begin_gml_time_instant_gml_related_time{}.gml_time_edge_gml_extent_xlink_href xml_buffer, energy_refurbishment_measure{}.energy_refurbishment_measure_energy_date_energy_date_of_event_energy_period_gml_time_period_gml_begin_gml_time_instant_gml_related_time{}.gml_time_edge_gml_extent_gml_time_period xml_xml, energy_refurbishment_measure{}.energy_refurbishment_measure_energy_date_energy_date_of_event_energy_period_gml_time_period_gml_begin_gml_time_instant_gml_related_time{}.gml_time_edge_gml_extent_gml_time_period_frame xml_buffer, energy_refurbishment_measure{}.energy_refurbishment_measure_energy_date_energy_date_of_event_energy_period_gml_time_period_gml_begin_gml_time_instant_gml_related_time{}.gml_time_edge_gml_extent_gml_time_period_gml_id xml_buffer, energy_refurbishment_measure{}.energy_refurbishment_measure_energy_date_energy_date_of_event_energy_period_gml_time_period_gml_begin_gml_time_instant_gml_related_time{}.gml_time_instant xml_xml, energy_refurbishment_measure{}.energy_refurbishment_measure_energy_date_energy_date_of_event_energy_period_gml_time_period_gml_begin_gml_time_instant_gml_related_time{}.gml_time_instant_frame xml_buffer, energy_refurbishment_measure{}.energy_refurbishment_measure_energy_date_energy_date_of_event_energy_period_gml_time_period_gml_begin_gml_time_instant_gml_related_time{}.gml_time_instant_gml_id xml_buffer, energy_refurbishment_measure{}.energy_refurbishment_measure_energy_date_energy_date_of_event_energy_period_gml_time_period_gml_begin_gml_time_instant_gml_related_time{}.gml_time_node_gml_id xml_buffer, energy_refurbishment_measure{}.energy_refurbishment_measure_energy_date_energy_date_of_event_energy_period_gml_time_period_gml_begin_gml_time_instant_gml_related_time{}.gml_time_node_gml_related_time{} xml_xml, energy_refurbishment_measure{}.energy_refurbishment_measure_energy_date_energy_date_of_event_energy_period_gml_time_period_gml_begin_gml_time_instant_gml_related_time{}.gml_time_node_gml_related_time{}.relativePosition xml_char(12), energy_refurbishment_measure{}.energy_refurbishment_measure_energy_date_energy_date_of_event_energy_period_gml_time_period_gml_begin_gml_time_instant_gml_related_time{}.gml_time_node_gml_related_time{}.xlink_href xml_buffer, energy_refurbishment_measure{}.energy_refurbishment_measure_energy_date_energy_date_of_event_energy_period_gml_time_period_gml_begin_gml_time_instant_gml_related_time{}.gml_time_node_gml_complex_xlink_href xml_buffer, energy_refurbishment_measure{}.energy_refurbishment_measure_energy_date_energy_date_of_event_energy_period_gml_time_period_gml_begin_gml_time_instant_gml_related_time{}.gml_time_node_gml_previous_edge{}.xlink_href xml_buffer, energy_refurbishment_measure{}.energy_refurbishment_measure_energy_date_energy_date_of_event_energy_period_gml_time_period_gml_begin_gml_time_instant_gml_related_time{}.gml_time_node_gml_previous_edge{}.gml_time_edge_gml_id xml_buffer, energy_refurbishment_measure{}.energy_refurbishment_measure_energy_date_energy_date_of_event_energy_period_gml_time_period_gml_begin_gml_time_instant_gml_related_time{}.gml_time_node_gml_previous_edge{}.gml_time_edge_gml_related_time{} xml_xml, energy_refurbishment_measure{}.energy_refurbishment_measure_energy_date_energy_date_of_event_energy_period_gml_time_period_gml_begin_gml_time_instant_gml_related_time{}.gml_time_node_gml_previous_edge{}.gml_time_edge_gml_related_time{}.relativePosition xml_char(12), energy_refurbishment_measure{}.energy_refurbishment_measure_energy_date_energy_date_of_event_energy_period_gml_time_period_gml_begin_gml_time_instant_gml_related_time{}.gml_time_node_gml_previous_edge{}.gml_time_edge_gml_related_time{}.xlink_href xml_buffer, energy_refurbishment_measure{}.energy_refurbishment_measure_energy_date_energy_date_of_event_energy_period_gml_time_period_gml_begin_gml_time_instant_gml_related_time{}.gml_time_node_gml_previous_edge{}.gml_time_edge_gml_complex_xlink_href xml_buffer, energy_refurbishment_measure{}.energy_refurbishment_measure_energy_date_energy_date_of_event_energy_period_gml_time_period_gml_begin_gml_time_instant_gml_related_time{}.gml_time_node_gml_previous_edge{}.gml_time_edge_gml_start_xlink_href xml_buffer,
      energy_refurbishment_measure{}.energy_refurbishment_measure_energy_date_energy_date_of_event_energy_period_gml_time_period_gml_begin_gml_time_instant_gml_related_time{}.gml_time_node_gml_previous_edge{}.gml_time_edge_gml_start_gml_time_node xml_xml, energy_refurbishment_measure{}.energy_refurbishment_measure_energy_date_energy_date_of_event_energy_period_gml_time_period_gml_begin_gml_time_instant_gml_related_time{}.gml_time_node_gml_previous_edge{}.gml_time_edge_gml_start_gml_time_node_gml_id xml_buffer, energy_refurbishment_measure{}.energy_refurbishment_measure_energy_date_energy_date_of_event_energy_period_gml_time_period_gml_begin_gml_time_instant_gml_related_time{}.gml_time_node_gml_previous_edge{}.gml_time_edge_gml_end_xlink_href xml_buffer, energy_refurbishment_measure{}.energy_refurbishment_measure_energy_date_energy_date_of_event_energy_period_gml_time_period_gml_begin_gml_time_instant_gml_related_time{}.gml_time_node_gml_previous_edge{}.gml_time_edge_gml_end_gml_time_node xml_xml, energy_refurbishment_measure{}.energy_refurbishment_measure_energy_date_energy_date_of_event_energy_period_gml_time_period_gml_begin_gml_time_instant_gml_related_time{}.gml_time_node_gml_previous_edge{}.gml_time_edge_gml_end_gml_time_node_gml_id xml_buffer, energy_refurbishment_measure{}.energy_refurbishment_measure_energy_date_energy_date_of_event_energy_period_gml_time_period_gml_begin_gml_time_instant_gml_related_time{}.gml_time_node_gml_previous_edge{}.gml_time_edge_gml_extent_xlink_href xml_buffer, energy_refurbishment_measure{}.energy_refurbishment_measure_energy_date_energy_date_of_event_energy_period_gml_time_period_gml_begin_gml_time_instant_gml_related_time{}.gml_time_node_gml_previous_edge{}.gml_time_edge_gml_extent_gml_time_period xml_xml, energy_refurbishment_measure{}.energy_refurbishment_measure_energy_date_energy_date_of_event_energy_period_gml_time_period_gml_begin_gml_time_instant_gml_related_time{}.gml_time_node_gml_previous_edge{}.gml_time_edge_gml_extent_gml_time_period_frame xml_buffer, energy_refurbishment_measure{}.energy_refurbishment_measure_energy_date_energy_date_of_event_energy_period_gml_time_period_gml_begin_gml_time_instant_gml_related_time{}.gml_time_node_gml_previous_edge{}.gml_time_edge_gml_extent_gml_time_period_gml_id xml_buffer, energy_refurbishment_measure{}.energy_refurbishment_measure_energy_date_energy_date_of_event_energy_period_gml_time_period_gml_begin_gml_time_instant_gml_related_time{}.gml_time_node_gml_next_edge{}.xlink_href xml_buffer, energy_refurbishment_measure{}.energy_refurbishment_measure_energy_date_energy_date_of_event_energy_period_gml_time_period_gml_begin_gml_time_instant_gml_related_time{}.gml_time_node_gml_next_edge{}.gml_time_edge_gml_id xml_buffer, energy_refurbishment_measure{}.energy_refurbishment_measure_energy_date_energy_date_of_event_energy_period_gml_time_period_gml_begin_gml_time_instant_gml_related_time{}.gml_time_node_gml_next_edge{}.gml_time_edge_gml_related_time{} xml_xml, energy_refurbishment_measure{}.energy_refurbishment_measure_energy_date_energy_date_of_event_energy_period_gml_time_period_gml_begin_gml_time_instant_gml_related_time{}.gml_time_node_gml_next_edge{}.gml_time_edge_gml_related_time{}.relativePosition xml_char(12), energy_refurbishment_measure{}.energy_refurbishment_measure_energy_date_energy_date_of_event_energy_period_gml_time_period_gml_begin_gml_time_instant_gml_related_time{}.gml_time_node_gml_next_edge{}.gml_time_edge_gml_related_time{}.xlink_href xml_buffer, energy_refurbishment_measure{}.energy_refurbishment_measure_energy_date_energy_date_of_event_energy_period_gml_time_period_gml_begin_gml_time_instant_gml_related_time{}.gml_time_node_gml_next_edge{}.gml_time_edge_gml_complex_xlink_href xml_buffer, energy_refurbishment_measure{}.energy_refurbishment_measure_energy_date_energy_date_of_event_energy_period_gml_time_period_gml_begin_gml_time_instant_gml_related_time{}.gml_time_node_gml_next_edge{}.gml_time_edge_gml_start_xlink_href xml_buffer, energy_refurbishment_measure{}.energy_refurbishment_measure_energy_date_energy_date_of_event_energy_period_gml_time_period_gml_begin_gml_time_instant_gml_related_time{}.gml_time_node_gml_next_edge{}.gml_time_edge_gml_start_gml_time_node xml_xml, energy_refurbishment_measure{}.energy_refurbishment_measure_energy_date_energy_date_of_event_energy_period_gml_time_period_gml_begin_gml_time_instant_gml_related_time{}.gml_time_node_gml_next_edge{}.gml_time_edge_gml_start_gml_time_node_gml_id xml_buffer, energy_refurbishment_measure{}.energy_refurbishment_measure_energy_date_energy_date_of_event_energy_period_gml_time_period_gml_begin_gml_time_instant_gml_related_time{}.gml_time_node_gml_next_edge{}.gml_time_edge_gml_end_xlink_href xml_buffer, energy_refurbishment_measure{}.energy_refurbishment_measure_energy_date_energy_date_of_event_energy_period_gml_time_period_gml_begin_gml_time_instant_gml_related_time{}.gml_time_node_gml_next_edge{}.gml_time_edge_gml_end_gml_time_node xml_xml, energy_refurbishment_measure{}.energy_refurbishment_measure_energy_date_energy_date_of_event_energy_period_gml_time_period_gml_begin_gml_time_instant_gml_related_time{}.gml_time_node_gml_next_edge{}.gml_time_edge_gml_end_gml_time_node_gml_id xml_buffer, energy_refurbishment_measure{}.energy_refurbishment_measure_energy_date_energy_date_of_event_energy_period_gml_time_period_gml_begin_gml_time_instant_gml_related_time{}.gml_time_node_gml_next_edge{}.gml_time_edge_gml_extent_xlink_href xml_buffer, energy_refurbishment_measure{}.energy_refurbishment_measure_energy_date_energy_date_of_event_energy_period_gml_time_period_gml_begin_gml_time_instant_gml_related_time{}.gml_time_node_gml_next_edge{}.gml_time_edge_gml_extent_gml_time_period xml_xml, energy_refurbishment_measure{}.energy_refurbishment_measure_energy_date_energy_date_of_event_energy_period_gml_time_period_gml_begin_gml_time_instant_gml_related_time{}.gml_time_node_gml_next_edge{}.gml_time_edge_gml_extent_gml_time_period_frame xml_buffer, energy_refurbishment_measure{}.energy_refurbishment_measure_energy_date_energy_date_of_event_energy_period_gml_time_period_gml_begin_gml_time_instant_gml_related_time{}.gml_time_node_gml_next_edge{}.gml_time_edge_gml_extent_gml_time_period_gml_id xml_buffer, energy_refurbishment_measure{}.energy_refurbishment_measure_energy_date_energy_date_of_event_energy_period_gml_time_period_gml_begin_gml_time_instant_gml_related_time{}.gml_time_node_gml_position_xlink_href xml_buffer, energy_refurbishment_measure{}.energy_refurbishment_measure_energy_date_energy_date_of_event_energy_period_gml_time_period_gml_begin_gml_time_instant_gml_related_time{}.gml_time_node_gml_position_gml_time_instant xml_xml, energy_refurbishment_measure{}.energy_refurbishment_measure_energy_date_energy_date_of_event_energy_period_gml_time_period_gml_begin_gml_time_instant_gml_related_time{}.gml_time_node_gml_position_gml_time_instant_frame xml_buffer, energy_refurbishment_measure{}.energy_refurbishment_measure_energy_date_energy_date_of_event_energy_period_gml_time_period_gml_begin_gml_time_instant_gml_related_time{}.gml_time_node_gml_position_gml_time_instant_gml_id xml_buffer, energy_refurbishment_measure{}.energy_refurbishment_measure_energy_date_energy_date_of_event_energy_period_gml_time_period_gml_begin_gml_time_instant_gml_related_time{}.gml_time_period xml_xml,
      energy_refurbishment_measure{}.energy_refurbishment_measure_energy_date_energy_date_of_event_energy_period_gml_time_period_gml_begin_gml_time_instant_gml_related_time{}.gml_time_period_frame xml_buffer, energy_refurbishment_measure{}.energy_refurbishment_measure_energy_date_energy_date_of_event_energy_period_gml_time_period_gml_begin_gml_time_instant_gml_related_time{}.gml_time_period_gml_id xml_buffer, energy_refurbishment_measure{}.energy_refurbishment_measure_energy_date_energy_date_of_event_energy_period_gml_time_period_gml_begin_gml_time_instant_gml_time_position xml_buffer, energy_refurbishment_measure{}.energy_refurbishment_measure_energy_date_energy_date_of_event_energy_period_gml_time_period_gml_begin_gml_time_instant_gml_time_position_frame xml_buffer, energy_refurbishment_measure{}.energy_refurbishment_measure_energy_date_energy_date_of_event_energy_period_gml_time_period_gml_begin_gml_time_instant_gml_time_position_calendarEraName xml_buffer, energy_refurbishment_measure{}.energy_refurbishment_measure_energy_date_energy_date_of_event_energy_period_gml_time_period_gml_begin_gml_time_instant_gml_time_position_indeterminatePosition xml_char(7), energy_refurbishment_measure{}.energy_refurbishment_measure_energy_date_energy_date_of_event_energy_period_gml_time_period_gml_end_position xml_buffer, energy_refurbishment_measure{}.energy_refurbishment_measure_energy_date_energy_date_of_event_energy_period_gml_time_period_gml_end_position_frame xml_buffer, energy_refurbishment_measure{}.energy_refurbishment_measure_energy_date_energy_date_of_event_energy_period_gml_time_period_gml_end_position_calendarEraName xml_buffer, energy_refurbishment_measure{}.energy_refurbishment_measure_energy_date_energy_date_of_event_energy_period_gml_time_period_gml_end_position_indeterminatePosition xml_char(7), energy_refurbishment_measure{}.energy_refurbishment_measure_energy_date_energy_date_of_event_energy_period_gml_time_period_gml_end_xlink_href xml_buffer, energy_refurbishment_measure{}.energy_refurbishment_measure_energy_date_energy_date_of_event_energy_period_gml_time_period_gml_end_gml_time_instant_frame xml_buffer, energy_refurbishment_measure{}.energy_refurbishment_measure_energy_date_energy_date_of_event_energy_period_gml_time_period_gml_end_gml_time_instant_gml_id xml_buffer, energy_refurbishment_measure{}.energy_refurbishment_measure_energy_date_energy_date_of_event_energy_period_gml_time_period_gml_end_gml_time_instant_gml_related_time{}.relativePosition xml_char(12), energy_refurbishment_measure{}.energy_refurbishment_measure_energy_date_energy_date_of_event_energy_period_gml_time_period_gml_end_gml_time_instant_gml_related_time{}.xlink_href xml_buffer, energy_refurbishment_measure{}.energy_refurbishment_measure_energy_date_energy_date_of_event_energy_period_gml_time_period_gml_end_gml_time_instant_gml_related_time{}.gml_time_edge_gml_id xml_buffer, energy_refurbishment_measure{}.energy_refurbishment_measure_energy_date_energy_date_of_event_energy_period_gml_time_period_gml_end_gml_time_instant_gml_related_time{}.gml_time_edge_gml_related_time{} xml_xml, energy_refurbishment_measure{}.energy_refurbishment_measure_energy_date_energy_date_of_event_energy_period_gml_time_period_gml_end_gml_time_instant_gml_related_time{}.gml_time_edge_gml_related_time{}.relativePosition xml_char(12), energy_refurbishment_measure{}.energy_refurbishment_measure_energy_date_energy_date_of_event_energy_period_gml_time_period_gml_end_gml_time_instant_gml_related_time{}.gml_time_edge_gml_related_time{}.xlink_href xml_buffer, energy_refurbishment_measure{}.energy_refurbishment_measure_energy_date_energy_date_of_event_energy_period_gml_time_period_gml_end_gml_time_instant_gml_related_time{}.gml_time_edge_gml_complex_xlink_href xml_buffer, energy_refurbishment_measure{}.energy_refurbishment_measure_energy_date_energy_date_of_event_energy_period_gml_time_period_gml_end_gml_time_instant_gml_related_time{}.gml_time_edge_gml_start_xlink_href xml_buffer, energy_refurbishment_measure{}.energy_refurbishment_measure_energy_date_energy_date_of_event_energy_period_gml_time_period_gml_end_gml_time_instant_gml_related_time{}.gml_time_edge_gml_start_gml_time_node_gml_id xml_buffer, energy_refurbishment_measure{}.energy_refurbishment_measure_energy_date_energy_date_of_event_energy_period_gml_time_period_gml_end_gml_time_instant_gml_related_time{}.gml_time_edge_gml_start_gml_time_node_gml_related_time{} xml_xml, energy_refurbishment_measure{}.energy_refurbishment_measure_energy_date_energy_date_of_event_energy_period_gml_time_period_gml_end_gml_time_instant_gml_related_time{}.gml_time_edge_gml_start_gml_time_node_gml_related_time{}.relativePosition xml_char(12), energy_refurbishment_measure{}.energy_refurbishment_measure_energy_date_energy_date_of_event_energy_period_gml_time_period_gml_end_gml_time_instant_gml_related_time{}.gml_time_edge_gml_start_gml_time_node_gml_related_time{}.xlink_href xml_buffer, energy_refurbishment_measure{}.energy_refurbishment_measure_energy_date_energy_date_of_event_energy_period_gml_time_period_gml_end_gml_time_instant_gml_related_time{}.gml_time_edge_gml_start_gml_time_node_gml_complex_xlink_href xml_buffer, energy_refurbishment_measure{}.energy_refurbishment_measure_energy_date_energy_date_of_event_energy_period_gml_time_period_gml_end_gml_time_instant_gml_related_time{}.gml_time_edge_gml_start_gml_time_node_gml_previous_edge{}.xlink_href xml_buffer, energy_refurbishment_measure{}.energy_refurbishment_measure_energy_date_energy_date_of_event_energy_period_gml_time_period_gml_end_gml_time_instant_gml_related_time{}.gml_time_edge_gml_start_gml_time_node_gml_previous_edge{}.gml_time_edge xml_xml, energy_refurbishment_measure{}.energy_refurbishment_measure_energy_date_energy_date_of_event_energy_period_gml_time_period_gml_end_gml_time_instant_gml_related_time{}.gml_time_edge_gml_start_gml_time_node_gml_previous_edge{}.gml_time_edge_gml_id xml_buffer, energy_refurbishment_measure{}.energy_refurbishment_measure_energy_date_energy_date_of_event_energy_period_gml_time_period_gml_end_gml_time_instant_gml_related_time{}.gml_time_edge_gml_start_gml_time_node_gml_next_edge{}.xlink_href xml_buffer,
      energy_refurbishment_measure{}.energy_refurbishment_measure_energy_date_energy_date_of_event_energy_period_gml_time_period_gml_end_gml_time_instant_gml_related_time{}.gml_time_edge_gml_start_gml_time_node_gml_next_edge{}.gml_time_edge xml_xml, energy_refurbishment_measure{}.energy_refurbishment_measure_energy_date_energy_date_of_event_energy_period_gml_time_period_gml_end_gml_time_instant_gml_related_time{}.gml_time_edge_gml_start_gml_time_node_gml_next_edge{}.gml_time_edge_gml_id xml_buffer, energy_refurbishment_measure{}.energy_refurbishment_measure_energy_date_energy_date_of_event_energy_period_gml_time_period_gml_end_gml_time_instant_gml_related_time{}.gml_time_edge_gml_start_gml_time_node_gml_position_xlink_href xml_buffer, energy_refurbishment_measure{}.energy_refurbishment_measure_energy_date_energy_date_of_event_energy_period_gml_time_period_gml_end_gml_time_instant_gml_related_time{}.gml_time_edge_gml_start_gml_time_node_gml_position_gml_time_instant xml_xml, energy_refurbishment_measure{}.energy_refurbishment_measure_energy_date_energy_date_of_event_energy_period_gml_time_period_gml_end_gml_time_instant_gml_related_time{}.gml_time_edge_gml_start_gml_time_node_gml_position_gml_time_instant_frame xml_buffer, energy_refurbishment_measure{}.energy_refurbishment_measure_energy_date_energy_date_of_event_energy_period_gml_time_period_gml_end_gml_time_instant_gml_related_time{}.gml_time_edge_gml_start_gml_time_node_gml_position_gml_time_instant_gml_id xml_buffer, energy_refurbishment_measure{}.energy_refurbishment_measure_energy_date_energy_date_of_event_energy_period_gml_time_period_gml_end_gml_time_instant_gml_related_time{}.gml_time_edge_gml_end_xlink_href xml_buffer, energy_refurbishment_measure{}.energy_refurbishment_measure_energy_date_energy_date_of_event_energy_period_gml_time_period_gml_end_gml_time_instant_gml_related_time{}.gml_time_edge_gml_end_gml_time_node_gml_id xml_buffer, energy_refurbishment_measure{}.energy_refurbishment_measure_energy_date_energy_date_of_event_energy_period_gml_time_period_gml_end_gml_time_instant_gml_related_time{}.gml_time_edge_gml_end_gml_time_node_gml_related_time{} xml_xml, energy_refurbishment_measure{}.energy_refurbishment_measure_energy_date_energy_date_of_event_energy_period_gml_time_period_gml_end_gml_time_instant_gml_related_time{}.gml_time_edge_gml_end_gml_time_node_gml_related_time{}.relativePosition xml_char(12), energy_refurbishment_measure{}.energy_refurbishment_measure_energy_date_energy_date_of_event_energy_period_gml_time_period_gml_end_gml_time_instant_gml_related_time{}.gml_time_edge_gml_end_gml_time_node_gml_related_time{}.xlink_href xml_buffer, energy_refurbishment_measure{}.energy_refurbishment_measure_energy_date_energy_date_of_event_energy_period_gml_time_period_gml_end_gml_time_instant_gml_related_time{}.gml_time_edge_gml_end_gml_time_node_gml_complex_xlink_href xml_buffer, energy_refurbishment_measure{}.energy_refurbishment_measure_energy_date_energy_date_of_event_energy_period_gml_time_period_gml_end_gml_time_instant_gml_related_time{}.gml_time_edge_gml_end_gml_time_node_gml_previous_edge{}.xlink_href xml_buffer, energy_refurbishment_measure{}.energy_refurbishment_measure_energy_date_energy_date_of_event_energy_period_gml_time_period_gml_end_gml_time_instant_gml_related_time{}.gml_time_edge_gml_end_gml_time_node_gml_previous_edge{}.gml_time_edge xml_xml, energy_refurbishment_measure{}.energy_refurbishment_measure_energy_date_energy_date_of_event_energy_period_gml_time_period_gml_end_gml_time_instant_gml_related_time{}.gml_time_edge_gml_end_gml_time_node_gml_previous_edge{}.gml_time_edge_gml_id xml_buffer, energy_refurbishment_measure{}.energy_refurbishment_measure_energy_date_energy_date_of_event_energy_period_gml_time_period_gml_end_gml_time_instant_gml_related_time{}.gml_time_edge_gml_end_gml_time_node_gml_next_edge{}.xlink_href xml_buffer, energy_refurbishment_measure{}.energy_refurbishment_measure_energy_date_energy_date_of_event_energy_period_gml_time_period_gml_end_gml_time_instant_gml_related_time{}.gml_time_edge_gml_end_gml_time_node_gml_next_edge{}.gml_time_edge xml_xml, energy_refurbishment_measure{}.energy_refurbishment_measure_energy_date_energy_date_of_event_energy_period_gml_time_period_gml_end_gml_time_instant_gml_related_time{}.gml_time_edge_gml_end_gml_time_node_gml_next_edge{}.gml_time_edge_gml_id xml_buffer, energy_refurbishment_measure{}.energy_refurbishment_measure_energy_date_energy_date_of_event_energy_period_gml_time_period_gml_end_gml_time_instant_gml_related_time{}.gml_time_edge_gml_end_gml_time_node_gml_position_xlink_href xml_buffer, energy_refurbishment_measure{}.energy_refurbishment_measure_energy_date_energy_date_of_event_energy_period_gml_time_period_gml_end_gml_time_instant_gml_related_time{}.gml_time_edge_gml_end_gml_time_node_gml_position_gml_time_instant xml_xml, energy_refurbishment_measure{}.energy_refurbishment_measure_energy_date_energy_date_of_event_energy_period_gml_time_period_gml_end_gml_time_instant_gml_related_time{}.gml_time_edge_gml_end_gml_time_node_gml_position_gml_time_instant_frame xml_buffer, energy_refurbishment_measure{}.energy_refurbishment_measure_energy_date_energy_date_of_event_energy_period_gml_time_period_gml_end_gml_time_instant_gml_related_time{}.gml_time_edge_gml_end_gml_time_node_gml_position_gml_time_instant_gml_id xml_buffer, energy_refurbishment_measure{}.energy_refurbishment_measure_energy_date_energy_date_of_event_energy_period_gml_time_period_gml_end_gml_time_instant_gml_related_time{}.gml_time_edge_gml_extent_xlink_href xml_buffer, energy_refurbishment_measure{}.energy_refurbishment_measure_energy_date_energy_date_of_event_energy_period_gml_time_period_gml_end_gml_time_instant_gml_related_time{}.gml_time_edge_gml_extent_gml_time_period xml_xml, energy_refurbishment_measure{}.energy_refurbishment_measure_energy_date_energy_date_of_event_energy_period_gml_time_period_gml_end_gml_time_instant_gml_related_time{}.gml_time_edge_gml_extent_gml_time_period_frame xml_buffer, energy_refurbishment_measure{}.energy_refurbishment_measure_energy_date_energy_date_of_event_energy_period_gml_time_period_gml_end_gml_time_instant_gml_related_time{}.gml_time_edge_gml_extent_gml_time_period_gml_id xml_buffer, energy_refurbishment_measure{}.energy_refurbishment_measure_energy_date_energy_date_of_event_energy_period_gml_time_period_gml_end_gml_time_instant_gml_related_time{}.gml_time_instant xml_xml, energy_refurbishment_measure{}.energy_refurbishment_measure_energy_date_energy_date_of_event_energy_period_gml_time_period_gml_end_gml_time_instant_gml_related_time{}.gml_time_instant_frame xml_buffer, energy_refurbishment_measure{}.energy_refurbishment_measure_energy_date_energy_date_of_event_energy_period_gml_time_period_gml_end_gml_time_instant_gml_related_time{}.gml_time_instant_gml_id xml_buffer, energy_refurbishment_measure{}.energy_refurbishment_measure_energy_date_energy_date_of_event_energy_period_gml_time_period_gml_end_gml_time_instant_gml_related_time{}.gml_time_node_gml_id xml_buffer,
      energy_refurbishment_measure{}.energy_refurbishment_measure_energy_date_energy_date_of_event_energy_period_gml_time_period_gml_end_gml_time_instant_gml_related_time{}.gml_time_node_gml_related_time{} xml_xml, energy_refurbishment_measure{}.energy_refurbishment_measure_energy_date_energy_date_of_event_energy_period_gml_time_period_gml_end_gml_time_instant_gml_related_time{}.gml_time_node_gml_related_time{}.relativePosition xml_char(12), energy_refurbishment_measure{}.energy_refurbishment_measure_energy_date_energy_date_of_event_energy_period_gml_time_period_gml_end_gml_time_instant_gml_related_time{}.gml_time_node_gml_related_time{}.xlink_href xml_buffer, energy_refurbishment_measure{}.energy_refurbishment_measure_energy_date_energy_date_of_event_energy_period_gml_time_period_gml_end_gml_time_instant_gml_related_time{}.gml_time_node_gml_complex_xlink_href xml_buffer, energy_refurbishment_measure{}.energy_refurbishment_measure_energy_date_energy_date_of_event_energy_period_gml_time_period_gml_end_gml_time_instant_gml_related_time{}.gml_time_node_gml_previous_edge{}.xlink_href xml_buffer, energy_refurbishment_measure{}.energy_refurbishment_measure_energy_date_energy_date_of_event_energy_period_gml_time_period_gml_end_gml_time_instant_gml_related_time{}.gml_time_node_gml_previous_edge{}.gml_time_edge_gml_id xml_buffer, energy_refurbishment_measure{}.energy_refurbishment_measure_energy_date_energy_date_of_event_energy_period_gml_time_period_gml_end_gml_time_instant_gml_related_time{}.gml_time_node_gml_previous_edge{}.gml_time_edge_gml_related_time{} xml_xml, energy_refurbishment_measure{}.energy_refurbishment_measure_energy_date_energy_date_of_event_energy_period_gml_time_period_gml_end_gml_time_instant_gml_related_time{}.gml_time_node_gml_previous_edge{}.gml_time_edge_gml_related_time{}.relativePosition xml_char(12), energy_refurbishment_measure{}.energy_refurbishment_measure_energy_date_energy_date_of_event_energy_period_gml_time_period_gml_end_gml_time_instant_gml_related_time{}.gml_time_node_gml_previous_edge{}.gml_time_edge_gml_related_time{}.xlink_href xml_buffer, energy_refurbishment_measure{}.energy_refurbishment_measure_energy_date_energy_date_of_event_energy_period_gml_time_period_gml_end_gml_time_instant_gml_related_time{}.gml_time_node_gml_previous_edge{}.gml_time_edge_gml_complex_xlink_href xml_buffer, energy_refurbishment_measure{}.energy_refurbishment_measure_energy_date_energy_date_of_event_energy_period_gml_time_period_gml_end_gml_time_instant_gml_related_time{}.gml_time_node_gml_previous_edge{}.gml_time_edge_gml_start_xlink_href xml_buffer, energy_refurbishment_measure{}.energy_refurbishment_measure_energy_date_energy_date_of_event_energy_period_gml_time_period_gml_end_gml_time_instant_gml_related_time{}.gml_time_node_gml_previous_edge{}.gml_time_edge_gml_start_gml_time_node xml_xml, energy_refurbishment_measure{}.energy_refurbishment_measure_energy_date_energy_date_of_event_energy_period_gml_time_period_gml_end_gml_time_instant_gml_related_time{}.gml_time_node_gml_previous_edge{}.gml_time_edge_gml_start_gml_time_node_gml_id xml_buffer, energy_refurbishment_measure{}.energy_refurbishment_measure_energy_date_energy_date_of_event_energy_period_gml_time_period_gml_end_gml_time_instant_gml_related_time{}.gml_time_node_gml_previous_edge{}.gml_time_edge_gml_end_xlink_href xml_buffer, energy_refurbishment_measure{}.energy_refurbishment_measure_energy_date_energy_date_of_event_energy_period_gml_time_period_gml_end_gml_time_instant_gml_related_time{}.gml_time_node_gml_previous_edge{}.gml_time_edge_gml_end_gml_time_node xml_xml, energy_refurbishment_measure{}.energy_refurbishment_measure_energy_date_energy_date_of_event_energy_period_gml_time_period_gml_end_gml_time_instant_gml_related_time{}.gml_time_node_gml_previous_edge{}.gml_time_edge_gml_end_gml_time_node_gml_id xml_buffer, energy_refurbishment_measure{}.energy_refurbishment_measure_energy_date_energy_date_of_event_energy_period_gml_time_period_gml_end_gml_time_instant_gml_related_time{}.gml_time_node_gml_previous_edge{}.gml_time_edge_gml_extent_xlink_href xml_buffer, energy_refurbishment_measure{}.energy_refurbishment_measure_energy_date_energy_date_of_event_energy_period_gml_time_period_gml_end_gml_time_instant_gml_related_time{}.gml_time_node_gml_previous_edge{}.gml_time_edge_gml_extent_gml_time_period xml_xml, energy_refurbishment_measure{}.energy_refurbishment_measure_energy_date_energy_date_of_event_energy_period_gml_time_period_gml_end_gml_time_instant_gml_related_time{}.gml_time_node_gml_previous_edge{}.gml_time_edge_gml_extent_gml_time_period_frame xml_buffer, energy_refurbishment_measure{}.energy_refurbishment_measure_energy_date_energy_date_of_event_energy_period_gml_time_period_gml_end_gml_time_instant_gml_related_time{}.gml_time_node_gml_previous_edge{}.gml_time_edge_gml_extent_gml_time_period_gml_id xml_buffer, energy_refurbishment_measure{}.energy_refurbishment_measure_energy_date_energy_date_of_event_energy_period_gml_time_period_gml_end_gml_time_instant_gml_related_time{}.gml_time_node_gml_next_edge{}.xlink_href xml_buffer, energy_refurbishment_measure{}.energy_refurbishment_measure_energy_date_energy_date_of_event_energy_period_gml_time_period_gml_end_gml_time_instant_gml_related_time{}.gml_time_node_gml_next_edge{}.gml_time_edge_gml_id xml_buffer, gml_description xml_buffer, gml_name xml_buffer, energy_refurbishment_measure{}.energy_refurbishment_measure_energy_date_energy_date_of_event_energy_period_gml_time_period_gml_end_gml_time_instant_gml_related_time{}.gml_time_node_gml_next_edge{}.gml_time_edge_gml_related_time{} xml_xml, energy_refurbishment_measure{}.energy_refurbishment_measure_energy_date_energy_date_of_event_energy_period_gml_time_period_gml_end_gml_time_instant_gml_related_time{}.gml_time_node_gml_next_edge{}.gml_time_edge_gml_related_time{}.relativePosition xml_char(12), energy_refurbishment_measure{}.energy_refurbishment_measure_energy_date_energy_date_of_event_energy_period_gml_time_period_gml_end_gml_time_instant_gml_related_time{}.gml_time_node_gml_next_edge{}.gml_time_edge_gml_related_time{}.xlink_href xml_buffer, energy_refurbishment_measure{}.energy_refurbishment_measure_energy_date_energy_date_of_event_energy_period_gml_time_period_gml_end_gml_time_instant_gml_related_time{}.gml_time_node_gml_next_edge{}.gml_time_edge_gml_complex_xlink_href xml_buffer, energy_refurbishment_measure{}.energy_refurbishment_measure_energy_date_energy_date_of_event_energy_period_gml_time_period_gml_end_gml_time_instant_gml_related_time{}.gml_time_node_gml_next_edge{}.gml_time_edge_gml_start_xlink_href xml_buffer, energy_refurbishment_measure{}.energy_refurbishment_measure_energy_date_energy_date_of_event_energy_period_gml_time_period_gml_end_gml_time_instant_gml_related_time{}.gml_time_node_gml_next_edge{}.gml_time_edge_gml_start_gml_time_node xml_xml,
      energy_refurbishment_measure{}.energy_refurbishment_measure_energy_date_energy_date_of_event_energy_period_gml_time_period_gml_end_gml_time_instant_gml_related_time{}.gml_time_node_gml_next_edge{}.gml_time_edge_gml_start_gml_time_node_gml_id xml_buffer, energy_refurbishment_measure{}.energy_refurbishment_measure_energy_date_energy_date_of_event_energy_period_gml_time_period_gml_end_gml_time_instant_gml_related_time{}.gml_time_node_gml_next_edge{}.gml_time_edge_gml_end_xlink_href xml_buffer, energy_refurbishment_measure{}.energy_refurbishment_measure_energy_date_energy_date_of_event_energy_period_gml_time_period_gml_end_gml_time_instant_gml_related_time{}.gml_time_node_gml_next_edge{}.gml_time_edge_gml_end_gml_time_node xml_xml, energy_refurbishment_measure{}.energy_refurbishment_measure_energy_date_energy_date_of_event_energy_period_gml_time_period_gml_end_gml_time_instant_gml_related_time{}.gml_time_node_gml_next_edge{}.gml_time_edge_gml_end_gml_time_node_gml_id xml_buffer, energy_refurbishment_measure{}.energy_refurbishment_measure_energy_date_energy_date_of_event_energy_period_gml_time_period_gml_end_gml_time_instant_gml_related_time{}.gml_time_node_gml_next_edge{}.gml_time_edge_gml_extent_xlink_href xml_buffer, energy_refurbishment_measure{}.energy_refurbishment_measure_energy_date_energy_date_of_event_energy_period_gml_time_period_gml_end_gml_time_instant_gml_related_time{}.gml_time_node_gml_next_edge{}.gml_time_edge_gml_extent_gml_time_period xml_xml, energy_refurbishment_measure{}.energy_refurbishment_measure_energy_date_energy_date_of_event_energy_period_gml_time_period_gml_end_gml_time_instant_gml_related_time{}.gml_time_node_gml_next_edge{}.gml_time_edge_gml_extent_gml_time_period_frame xml_buffer, energy_refurbishment_measure{}.energy_refurbishment_measure_energy_date_energy_date_of_event_energy_period_gml_time_period_gml_end_gml_time_instant_gml_related_time{}.gml_time_node_gml_next_edge{}.gml_time_edge_gml_extent_gml_time_period_gml_id xml_buffer, energy_refurbishment_measure{}.energy_refurbishment_measure_energy_date_energy_date_of_event_energy_period_gml_time_period_gml_end_gml_time_instant_gml_related_time{}.gml_time_node_gml_position_xlink_href xml_buffer, energy_refurbishment_measure{}.energy_refurbishment_measure_energy_date_energy_date_of_event_energy_period_gml_time_period_gml_end_gml_time_instant_gml_related_time{}.gml_time_node_gml_position_gml_time_instant xml_xml, energy_refurbishment_measure{}.energy_refurbishment_measure_energy_date_energy_date_of_event_energy_period_gml_time_period_gml_end_gml_time_instant_gml_related_time{}.gml_time_node_gml_position_gml_time_instant_frame xml_buffer, energy_refurbishment_measure{}.energy_refurbishment_measure_energy_date_energy_date_of_event_energy_period_gml_time_period_gml_end_gml_time_instant_gml_related_time{}.gml_time_node_gml_position_gml_time_instant_gml_id xml_buffer, energy_refurbishment_measure{}.energy_refurbishment_measure_energy_date_energy_date_of_event_energy_period_gml_time_period_gml_end_gml_time_instant_gml_related_time{}.gml_time_period xml_xml, energy_refurbishment_measure{}.energy_refurbishment_measure_energy_date_energy_date_of_event_energy_period_gml_time_period_gml_end_gml_time_instant_gml_related_time{}.gml_time_period_frame xml_buffer, energy_refurbishment_measure{}.energy_refurbishment_measure_energy_date_energy_date_of_event_energy_period_gml_time_period_gml_end_gml_time_instant_gml_related_time{}.gml_time_period_gml_id xml_buffer, energy_refurbishment_measure{}.energy_refurbishment_measure_energy_date_energy_date_of_event_energy_period_gml_time_period_gml_end_gml_time_instant_gml_time_position xml_buffer, energy_refurbishment_measure{}.energy_refurbishment_measure_energy_date_energy_date_of_event_energy_period_gml_time_period_gml_end_gml_time_instant_gml_time_position_frame xml_buffer, energy_refurbishment_measure{}.energy_refurbishment_measure_energy_date_energy_date_of_event_energy_period_gml_time_period_gml_end_gml_time_instant_gml_time_position_calendarEraName xml_buffer, energy_refurbishment_measure{}.energy_refurbishment_measure_energy_date_energy_date_of_event_energy_period_gml_time_period_gml_end_gml_time_instant_gml_time_position_indeterminatePosition xml_char(7), energy_refurbishment_measure{}.energy_refurbishment_measure_energy_date_energy_date_of_event_energy_period_gml_time_period_gml_duration xml_buffer, energy_refurbishment_measure{}.energy_refurbishment_measure_energy_date_energy_date_of_event_energy_period_gml_time_period_gml_time_interval xml_real64, energy_refurbishment_measure{}.energy_refurbishment_measure_energy_date_energy_date_of_event_energy_period_gml_time_period_gml_time_interval_unit xml_buffer, energy_refurbishment_measure{}.energy_refurbishment_measure_energy_date_energy_date_of_event_energy_period_gml_time_period_gml_time_interval_radix xml_uint64, energy_refurbishment_measure{}.energy_refurbishment_measure_energy_date_energy_date_of_event_energy_period_gml_time_period_gml_time_interval_factor xml_int64, energy_refurbishment_measure{}.energy_refurbishment_measure_energy_level xml_buffer, energy_refurbishment_measure{}.energy_refurbishment_measure_energy_level_codeSpace xml_buffer, energy_refurbishment_measure{}.energy_refurbishment_measure_energy_description xml_buffer, energy_construction_xlink_href xml_buffer, energy_contains{}.xlink_href xml_buffer, energy_delimits{}.xlink_href xml_buffer,
      energy_relates_to{}.xlink_href xml_buffer
    -> Tester_2
Tester_2
    BOOL_OP = OR
    TEST_CLAUSE = TEST @Value(gml_id) = id_building_1_therm_bdry_1
    TEST_MODE = TEST
    PASSED -> AttributeCreator_10
    FAILED -> ThermalBoundary (writer CITYGML_2)
AttributeCreator_10
    ATTR_TABLE = SET_TO energy_relates_to{0}.xlink_href = #id_building_1_roofsurface_1
    -> ThermalBoundary (writer CITYGML_2)
ThermalBoundary (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_thermal_boundary_type xml_char(17), energy_azimuth xml_real64, energy_azimuth_units xml_buffer, energy_inclination xml_real64, energy_inclination_units xml_buffer, energy_area xml_real64, energy_area_units xml_buffer, citygml_level_of_detail{} xml_buffer, energy_refurbishment_measure{}.energy_refurbishment_measure_energy_date_energy_date_of_event_energy_instant xml_buffer, energy_refurbishment_measure{}.energy_refurbishment_measure_energy_date_energy_date_of_event_energy_instant_frame xml_buffer, energy_refurbishment_measure{}.energy_refurbishment_measure_energy_date_energy_date_of_event_energy_instant_calendarEraName xml_buffer, energy_refurbishment_measure{}.energy_refurbishment_measure_energy_date_energy_date_of_event_energy_instant_indeterminatePosition xml_char(7), energy_refurbishment_measure{}.energy_refurbishment_measure_energy_date_energy_date_of_event_energy_period_xlink_href xml_buffer, energy_refurbishment_measure{}.energy_refurbishment_measure_energy_date_energy_date_of_event_energy_period_gml_time_period_frame xml_buffer,
      energy_refurbishment_measure{}.energy_refurbishment_measure_energy_date_energy_date_of_event_energy_period_gml_time_period_gml_id xml_buffer, energy_refurbishment_measure{}.energy_refurbishment_measure_energy_date_energy_date_of_event_energy_period_gml_time_period_gml_related_time{}.relativePosition xml_char(12), energy_refurbishment_measure{}.energy_refurbishment_measure_energy_date_energy_date_of_event_energy_period_gml_time_period_gml_related_time{}.xlink_href xml_buffer, energy_refurbishment_measure{}.energy_refurbishment_measure_energy_date_energy_date_of_event_energy_period_gml_time_period_gml_related_time{}.gml_time_edge_gml_id xml_buffer, energy_refurbishment_measure{}.energy_refurbishment_measure_energy_date_energy_date_of_event_energy_period_gml_time_period_gml_related_time{}.gml_time_edge_gml_related_time{} xml_xml, energy_refurbishment_measure{}.energy_refurbishment_measure_energy_date_energy_date_of_event_energy_period_gml_time_period_gml_related_time{}.gml_time_edge_gml_related_time{}.relativePosition xml_char(12), energy_refurbishment_measure{}.energy_refurbishment_measure_energy_date_energy_date_of_event_energy_period_gml_time_period_gml_related_time{}.gml_time_edge_gml_related_time{}.xlink_href xml_buffer, energy_refurbishment_measure{}.energy_refurbishment_measure_energy_date_energy_date_of_event_energy_period_gml_time_period_gml_related_time{}.gml_time_edge_gml_complex_xlink_href xml_buffer, energy_refurbishment_measure{}.energy_refurbishment_measure_energy_date_energy_date_of_event_energy_period_gml_time_period_gml_related_time{}.gml_time_edge_gml_start_xlink_href xml_buffer, energy_refurbishment_measure{}.energy_refurbishment_measure_energy_date_energy_date_of_event_energy_period_gml_time_period_gml_related_time{}.gml_time_edge_gml_start_gml_time_node_gml_id xml_buffer, energy_refurbishment_measure{}.energy_refurbishment_measure_energy_date_energy_date_of_event_energy_period_gml_time_period_gml_related_time{}.gml_time_edge_gml_start_gml_time_node_gml_related_time{} xml_xml, energy_refurbishment_measure{}.energy_refurbishment_measure_energy_date_energy_date_of_event_energy_period_gml_time_period_gml_related_time{}.gml_time_edge_gml_start_gml_time_node_gml_related_time{}.relativePosition xml_char(12), energy_refurbishment_measure{}.energy_refurbishment_measure_energy_date_energy_date_of_event_energy_period_gml_time_period_gml_related_time{}.gml_time_edge_gml_start_gml_time_node_gml_related_time{}.xlink_href xml_buffer, energy_refurbishment_measure{}.energy_refurbishment_measure_energy_date_energy_date_of_event_energy_period_gml_time_period_gml_related_time{}.gml_time_edge_gml_start_gml_time_node_gml_complex_xlink_href xml_buffer, energy_refurbishment_measure{}.energy_refurbishment_measure_energy_date_energy_date_of_event_energy_period_gml_time_period_gml_related_time{}.gml_time_edge_gml_start_gml_time_node_gml_previous_edge{}.xlink_href xml_buffer, energy_refurbishment_measure{}.energy_refurbishment_measure_energy_date_energy_date_of_event_energy_period_gml_time_period_gml_related_time{}.gml_time_edge_gml_start_gml_time_node_gml_previous_edge{}.gml_time_edge xml_xml, energy_refurbishment_measure{}.energy_refurbishment_measure_energy_date_energy_date_of_event_energy_period_gml_time_period_gml_related_time{}.gml_time_edge_gml_start_gml_time_node_gml_previous_edge{}.gml_time_edge_gml_id xml_buffer, energy_refurbishment_measure{}.energy_refurbishment_measure_energy_date_energy_date_of_event_energy_period_gml_time_period_gml_related_time{}.gml_time_edge_gml_start_gml_time_node_gml_next_edge{}.xlink_href xml_buffer, energy_refurbishment_measure{}.energy_refurbishment_measure_energy_date_energy_date_of_event_energy_period_gml_time_period_gml_related_time{}.gml_time_edge_gml_start_gml_time_node_gml_next_edge{}.gml_time_edge xml_xml, energy_refurbishment_measure{}.energy_refurbishment_measure_energy_date_energy_date_of_event_energy_period_gml_time_period_gml_related_time{}.gml_time_edge_gml_start_gml_time_node_gml_next_edge{}.gml_time_edge_gml_id xml_buffer, energy_refurbishment_measure{}.energy_refurbishment_measure_energy_date_energy_date_of_event_energy_period_gml_time_period_gml_related_time{}.gml_time_edge_gml_start_gml_time_node_gml_position_xlink_href xml_buffer, energy_refurbishment_measure{}.energy_refurbishment_measure_energy_date_energy_date_of_event_energy_period_gml_time_period_gml_related_time{}.gml_time_edge_gml_start_gml_time_node_gml_position_gml_time_instant_frame xml_buffer, energy_refurbishment_measure{}.energy_refurbishment_measure_energy_date_energy_date_of_event_energy_period_gml_time_period_gml_related_time{}.gml_time_edge_gml_start_gml_time_node_gml_position_gml_time_instant_gml_id xml_buffer, energy_refurbishment_measure{}.energy_refurbishment_measure_energy_date_energy_date_of_event_energy_period_gml_time_period_gml_related_time{}.gml_time_edge_gml_start_gml_time_node_gml_position_gml_time_instant_gml_related_time{} xml_xml, energy_refurbishment_measure{}.energy_refurbishment_measure_energy_date_energy_date_of_event_energy_period_gml_time_period_gml_related_time{}.gml_time_edge_gml_start_gml_time_node_gml_position_gml_time_instant_gml_related_time{}.relativePosition xml_char(12), energy_refurbishment_measure{}.energy_refurbishment_measure_energy_date_energy_date_of_event_energy_period_gml_time_period_gml_related_time{}.gml_time_edge_gml_start_gml_time_node_gml_position_gml_time_instant_gml_related_time{}.xlink_href xml_buffer, energy_refurbishment_measure{}.energy_refurbishment_measure_energy_date_energy_date_of_event_energy_period_gml_time_period_gml_related_time{}.gml_time_edge_gml_start_gml_time_node_gml_position_gml_time_instant_gml_time_position xml_buffer, energy_refurbishment_measure{}.energy_refurbishment_measure_energy_date_energy_date_of_event_energy_period_gml_time_period_gml_related_time{}.gml_time_edge_gml_start_gml_time_node_gml_position_gml_time_instant_gml_time_position_frame xml_buffer, energy_refurbishment_measure{}.energy_refurbishment_measure_energy_date_energy_date_of_event_energy_period_gml_time_period_gml_related_time{}.gml_time_edge_gml_start_gml_time_node_gml_position_gml_time_instant_gml_time_position_calendarEraName xml_buffer, energy_refurbishment_measure{}.energy_refurbishment_measure_energy_date_energy_date_of_event_energy_period_gml_time_period_gml_related_time{}.gml_time_edge_gml_start_gml_time_node_gml_position_gml_time_instant_gml_time_position_indeterminatePosition xml_char(7),
      energy_refurbishment_measure{}.energy_refurbishment_measure_energy_date_energy_date_of_event_energy_period_gml_time_period_gml_related_time{}.gml_time_edge_gml_end_xlink_href xml_buffer, energy_refurbishment_measure{}.energy_refurbishment_measure_energy_date_energy_date_of_event_energy_period_gml_time_period_gml_related_time{}.gml_time_edge_gml_end_gml_time_node_gml_id xml_buffer, energy_refurbishment_measure{}.energy_refurbishment_measure_energy_date_energy_date_of_event_energy_period_gml_time_period_gml_related_time{}.gml_time_edge_gml_end_gml_time_node_gml_related_time{} xml_xml, energy_refurbishment_measure{}.energy_refurbishment_measure_energy_date_energy_date_of_event_energy_period_gml_time_period_gml_related_time{}.gml_time_edge_gml_end_gml_time_node_gml_related_time{}.relativePosition xml_char(12), energy_refurbishment_measure{}.energy_refurbishment_measure_energy_date_energy_date_of_event_energy_period_gml_time_period_gml_related_time{}.gml_time_edge_gml_end_gml_time_node_gml_related_time{}.xlink_href xml_buffer, energy_refurbishment_measure{}.energy_refurbishment_measure_energy_date_energy_date_of_event_energy_period_gml_time_period_gml_related_time{}.gml_time_edge_gml_end_gml_time_node_gml_complex_xlink_href xml_buffer, energy_refurbishment_measure{}.energy_refurbishment_measure_energy_date_energy_date_of_event_energy_period_gml_time_period_gml_related_time{}.gml_time_edge_gml_end_gml_time_node_gml_previous_edge{}.xlink_href xml_buffer, energy_refurbishment_measure{}.energy_refurbishment_measure_energy_date_energy_date_of_event_energy_period_gml_time_period_gml_related_time{}.gml_time_edge_gml_end_gml_time_node_gml_previous_edge{}.gml_time_edge xml_xml, energy_refurbishment_measure{}.energy_refurbishment_measure_energy_date_energy_date_of_event_energy_period_gml_time_period_gml_related_time{}.gml_time_edge_gml_end_gml_time_node_gml_previous_edge{}.gml_time_edge_gml_id xml_buffer, energy_refurbishment_measure{}.energy_refurbishment_measure_energy_date_energy_date_of_event_energy_period_gml_time_period_gml_related_time{}.gml_time_edge_gml_end_gml_time_node_gml_next_edge{}.xlink_href xml_buffer, energy_refurbishment_measure{}.energy_refurbishment_measure_energy_date_energy_date_of_event_energy_period_gml_time_period_gml_related_time{}.gml_time_edge_gml_end_gml_time_node_gml_next_edge{}.gml_time_edge xml_xml, energy_refurbishment_measure{}.energy_refurbishment_measure_energy_date_energy_date_of_event_energy_period_gml_time_period_gml_related_time{}.gml_time_edge_gml_end_gml_time_node_gml_next_edge{}.gml_time_edge_gml_id xml_buffer, energy_refurbishment_measure{}.energy_refurbishment_measure_energy_date_energy_date_of_event_energy_period_gml_time_period_gml_related_time{}.gml_time_edge_gml_end_gml_time_node_gml_position_xlink_href xml_buffer, energy_refurbishment_measure{}.energy_refurbishment_measure_energy_date_energy_date_of_event_energy_period_gml_time_period_gml_related_time{}.gml_time_edge_gml_end_gml_time_node_gml_position_gml_time_instant_frame xml_buffer, energy_refurbishment_measure{}.energy_refurbishment_measure_energy_date_energy_date_of_event_energy_period_gml_time_period_gml_related_time{}.gml_time_edge_gml_end_gml_time_node_gml_position_gml_time_instant_gml_id xml_buffer, energy_refurbishment_measure{}.energy_refurbishment_measure_energy_date_energy_date_of_event_energy_period_gml_time_period_gml_related_time{}.gml_time_edge_gml_end_gml_time_node_gml_position_gml_time_instant_gml_related_time{} xml_xml, energy_refurbishment_measure{}.energy_refurbishment_measure_energy_date_energy_date_of_event_energy_period_gml_time_period_gml_related_time{}.gml_time_edge_gml_end_gml_time_node_gml_position_gml_time_instant_gml_related_time{}.relativePosition xml_char(12), energy_refurbishment_measure{}.energy_refurbishment_measure_energy_date_energy_date_of_event_energy_period_gml_time_period_gml_related_time{}.gml_time_edge_gml_end_gml_time_node_gml_position_gml_time_instant_gml_related_time{}.xlink_href xml_buffer, energy_refurbishment_measure{}.energy_refurbishment_measure_energy_date_energy_date_of_event_energy_period_gml_time_period_gml_related_time{}.gml_time_edge_gml_end_gml_time_node_gml_position_gml_time_instant_gml_time_position xml_buffer, energy_refurbishment_measure{}.energy_refurbishment_measure_energy_date_energy_date_of_event_energy_period_gml_time_period_gml_related_time{}.gml_time_edge_gml_end_gml_time_node_gml_position_gml_time_instant_gml_time_position_frame xml_buffer, energy_refurbishment_measure{}.energy_refurbishment_measure_energy_date_energy_date_of_event_energy_period_gml_time_period_gml_related_time{}.gml_time_edge_gml_end_gml_time_node_gml_position_gml_time_instant_gml_time_position_calendarEraName xml_buffer, energy_refurbishment_measure{}.energy_refurbishment_measure_energy_date_energy_date_of_event_energy_period_gml_time_period_gml_related_time{}.gml_time_edge_gml_end_gml_time_node_gml_position_gml_time_instant_gml_time_position_indeterminatePosition xml_char(7), energy_refurbishment_measure{}.energy_refurbishment_measure_energy_date_energy_date_of_event_energy_period_gml_time_period_gml_related_time{}.gml_time_edge_gml_extent_xlink_href xml_buffer, energy_refurbishment_measure{}.energy_refurbishment_measure_energy_date_energy_date_of_event_energy_period_gml_time_period_gml_related_time{}.gml_time_edge_gml_extent_gml_time_period xml_xml, energy_refurbishment_measure{}.energy_refurbishment_measure_energy_date_energy_date_of_event_energy_period_gml_time_period_gml_related_time{}.gml_time_edge_gml_extent_gml_time_period_frame xml_buffer, energy_refurbishment_measure{}.energy_refurbishment_measure_energy_date_energy_date_of_event_energy_period_gml_time_period_gml_related_time{}.gml_time_edge_gml_extent_gml_time_period_gml_id xml_buffer, energy_refurbishment_measure{}.energy_refurbishment_measure_energy_date_energy_date_of_event_energy_period_gml_time_period_gml_related_time{}.gml_time_instant_frame xml_buffer, energy_refurbishment_measure{}.energy_refurbishment_measure_energy_date_energy_date_of_event_energy_period_gml_time_period_gml_related_time{}.gml_time_instant_gml_id xml_buffer, energy_refurbishment_measure{}.energy_refurbishment_measure_energy_date_energy_date_of_event_energy_period_gml_time_period_gml_related_time{}.gml_time_instant_gml_related_time{} xml_xml, energy_refurbishment_measure{}.energy_refurbishment_measure_energy_date_energy_date_of_event_energy_period_gml_time_period_gml_related_time{}.gml_time_instant_gml_related_time{}.relativePosition xml_char(12),
      energy_refurbishment_measure{}.energy_refurbishment_measure_energy_date_energy_date_of_event_energy_period_gml_time_period_gml_related_time{}.gml_time_instant_gml_related_time{}.xlink_href xml_buffer, energy_refurbishment_measure{}.energy_refurbishment_measure_energy_date_energy_date_of_event_energy_period_gml_time_period_gml_related_time{}.gml_time_instant_gml_time_position xml_buffer, energy_refurbishment_measure{}.energy_refurbishment_measure_energy_date_energy_date_of_event_energy_period_gml_time_period_gml_related_time{}.gml_time_instant_gml_time_position_frame xml_buffer, energy_refurbishment_measure{}.energy_refurbishment_measure_energy_date_energy_date_of_event_energy_period_gml_time_period_gml_related_time{}.gml_time_instant_gml_time_position_calendarEraName xml_buffer, energy_refurbishment_measure{}.energy_refurbishment_measure_energy_date_energy_date_of_event_energy_period_gml_time_period_gml_related_time{}.gml_time_instant_gml_time_position_indeterminatePosition xml_char(7), energy_refurbishment_measure{}.energy_refurbishment_measure_energy_date_energy_date_of_event_energy_period_gml_time_period_gml_related_time{}.gml_time_node_gml_id xml_buffer, energy_refurbishment_measure{}.energy_refurbishment_measure_energy_date_energy_date_of_event_energy_period_gml_time_period_gml_related_time{}.gml_time_node_gml_related_time{} xml_xml, energy_refurbishment_measure{}.energy_refurbishment_measure_energy_date_energy_date_of_event_energy_period_gml_time_period_gml_related_time{}.gml_time_node_gml_related_time{}.relativePosition xml_char(12), energy_refurbishment_measure{}.energy_refurbishment_measure_energy_date_energy_date_of_event_energy_period_gml_time_period_gml_related_time{}.gml_time_node_gml_related_time{}.xlink_href xml_buffer, energy_refurbishment_measure{}.energy_refurbishment_measure_energy_date_energy_date_of_event_energy_period_gml_time_period_gml_related_time{}.gml_time_node_gml_complex_xlink_href xml_buffer, energy_refurbishment_measure{}.energy_refurbishment_measure_energy_date_energy_date_of_event_energy_period_gml_time_period_gml_related_time{}.gml_time_node_gml_previous_edge{}.xlink_href xml_buffer, energy_refurbishment_measure{}.energy_refurbishment_measure_energy_date_energy_date_of_event_energy_period_gml_time_period_gml_related_time{}.gml_time_node_gml_previous_edge{}.gml_time_edge_gml_id xml_buffer, energy_refurbishment_measure{}.energy_refurbishment_measure_energy_date_energy_date_of_event_energy_period_gml_time_period_gml_related_time{}.gml_time_node_gml_previous_edge{}.gml_time_edge_gml_related_time{} xml_xml, energy_refurbishment_measure{}.energy_refurbishment_measure_energy_date_energy_date_of_event_energy_period_gml_time_period_gml_related_time{}.gml_time_node_gml_previous_edge{}.gml_time_edge_gml_related_time{}.relativePosition xml_char(12), energy_refurbishment_measure{}.energy_refurbishment_measure_energy_date_energy_date_of_event_energy_period_gml_time_period_gml_related_time{}.gml_time_node_gml_previous_edge{}.gml_time_edge_gml_related_time{}.xlink_href xml_buffer, energy_refurbishment_measure{}.energy_refurbishment_measure_energy_date_energy_date_of_event_energy_period_gml_time_period_gml_related_time{}.gml_time_node_gml_previous_edge{}.gml_time_edge_gml_complex_xlink_href xml_buffer, energy_refurbishment_measure{}.energy_refurbishment_measure_energy_date_energy_date_of_event_energy_period_gml_time_period_gml_related_time{}.gml_time_node_gml_previous_edge{}.gml_time_edge_gml_start_xlink_href xml_buffer, energy_refurbishment_measure{}.energy_refurbishment_measure_energy_date_energy_date_of_event_energy_period_gml_time_period_gml_related_time{}.gml_time_node_gml_previous_edge{}.gml_time_edge_gml_start_gml_time_node xml_xml, energy_refurbishment_measure{}.energy_refurbishment_measure_energy_date_energy_date_of_event_energy_period_gml_time_period_gml_related_time{}.gml_time_node_gml_previous_edge{}.gml_time_edge_gml_start_gml_time_node_gml_id xml_buffer, energy_refurbishment_measure{}.energy_refurbishment_measure_energy_date_energy_date_of_event_energy_period_gml_time_period_gml_related_time{}.gml_time_node_gml_previous_edge{}.gml_time_edge_gml_end_xlink_href xml_buffer, energy_refurbishment_measure{}.energy_refurbishment_measure_energy_date_energy_date_of_event_energy_period_gml_time_period_gml_related_time{}.gml_time_node_gml_previous_edge{}.gml_time_edge_gml_end_gml_time_node xml_xml, energy_refurbishment_measure{}.energy_refurbishment_measure_energy_date_energy_date_of_event_energy_period_gml_time_period_gml_related_time{}.gml_time_node_gml_previous_edge{}.gml_time_edge_gml_end_gml_time_node_gml_id xml_buffer, energy_refurbishment_measure{}.energy_refurbishment_measure_energy_date_energy_date_of_event_energy_period_gml_time_period_gml_related_time{}.gml_time_node_gml_previous_edge{}.gml_time_edge_gml_extent_xlink_href xml_buffer, energy_refurbishment_measure{}.energy_refurbishment_measure_energy_date_energy_date_of_event_energy_period_gml_time_period_gml_related_time{}.gml_time_node_gml_previous_edge{}.gml_time_edge_gml_extent_gml_time_period xml_xml, energy_refurbishment_measure{}.energy_refurbishment_measure_energy_date_energy_date_of_event_energy_period_gml_time_period_gml_related_time{}.gml_time_node_gml_previous_edge{}.gml_time_edge_gml_extent_gml_time_period_frame xml_buffer, energy_refurbishment_measure{}.energy_refurbishment_measure_energy_date_energy_date_of_event_energy_period_gml_time_period_gml_related_time{}.gml_time_node_gml_previous_edge{}.gml_time_edge_gml_extent_gml_time_period_gml_id xml_buffer, energy_refurbishment_measure{}.energy_refurbishment_measure_energy_date_energy_date_of_event_energy_period_gml_time_period_gml_related_time{}.gml_time_node_gml_next_edge{}.xlink_href xml_buffer, energy_refurbishment_measure{}.energy_refurbishment_measure_energy_date_energy_date_of_event_energy_period_gml_time_period_gml_related_time{}.gml_time_node_gml_next_edge{}.gml_time_edge_gml_id xml_buffer, energy_refurbishment_measure{}.energy_refurbishment_measure_energy_date_energy_date_of_event_energy_period_gml_time_period_gml_related_time{}.gml_time_node_gml_next_edge{}.gml_time_edge_gml_related_time{} xml_xml, energy_refurbishment_measure{}.energy_refurbishment_measure_energy_date_energy_date_of_event_energy_period_gml_time_period_gml_related_time{}.gml_time_node_gml_next_edge{}.gml_time_edge_gml_related_time{}.relativePosition xml_char(12),
      energy_refurbishment_measure{}.energy_refurbishment_measure_energy_date_energy_date_of_event_energy_period_gml_time_period_gml_related_time{}.gml_time_node_gml_next_edge{}.gml_time_edge_gml_related_time{}.xlink_href xml_buffer, energy_refurbishment_measure{}.energy_refurbishment_measure_energy_date_energy_date_of_event_energy_period_gml_time_period_gml_related_time{}.gml_time_node_gml_next_edge{}.gml_time_edge_gml_complex_xlink_href xml_buffer, energy_refurbishment_measure{}.energy_refurbishment_measure_energy_date_energy_date_of_event_energy_period_gml_time_period_gml_related_time{}.gml_time_node_gml_next_edge{}.gml_time_edge_gml_start_xlink_href xml_buffer, energy_refurbishment_measure{}.energy_refurbishment_measure_energy_date_energy_date_of_event_energy_period_gml_time_period_gml_related_time{}.gml_time_node_gml_next_edge{}.gml_time_edge_gml_start_gml_time_node xml_xml, energy_refurbishment_measure{}.energy_refurbishment_measure_energy_date_energy_date_of_event_energy_period_gml_time_period_gml_related_time{}.gml_time_node_gml_next_edge{}.gml_time_edge_gml_start_gml_time_node_gml_id xml_buffer, energy_refurbishment_measure{}.energy_refurbishment_measure_energy_date_energy_date_of_event_energy_period_gml_time_period_gml_related_time{}.gml_time_node_gml_next_edge{}.gml_time_edge_gml_end_xlink_href xml_buffer, energy_refurbishment_measure{}.energy_refurbishment_measure_energy_date_energy_date_of_event_energy_period_gml_time_period_gml_related_time{}.gml_time_node_gml_next_edge{}.gml_time_edge_gml_end_gml_time_node xml_xml, energy_refurbishment_measure{}.energy_refurbishment_measure_energy_date_energy_date_of_event_energy_period_gml_time_period_gml_related_time{}.gml_time_node_gml_next_edge{}.gml_time_edge_gml_end_gml_time_node_gml_id xml_buffer, energy_refurbishment_measure{}.energy_refurbishment_measure_energy_date_energy_date_of_event_energy_period_gml_time_period_gml_related_time{}.gml_time_node_gml_next_edge{}.gml_time_edge_gml_extent_xlink_href xml_buffer, energy_refurbishment_measure{}.energy_refurbishment_measure_energy_date_energy_date_of_event_energy_period_gml_time_period_gml_related_time{}.gml_time_node_gml_next_edge{}.gml_time_edge_gml_extent_gml_time_period xml_xml, energy_refurbishment_measure{}.energy_refurbishment_measure_energy_date_energy_date_of_event_energy_period_gml_time_period_gml_related_time{}.gml_time_node_gml_next_edge{}.gml_time_edge_gml_extent_gml_time_period_frame xml_buffer, energy_refurbishment_measure{}.energy_refurbishment_measure_energy_date_energy_date_of_event_energy_period_gml_time_period_gml_related_time{}.gml_time_node_gml_next_edge{}.gml_time_edge_gml_extent_gml_time_period_gml_id xml_buffer, energy_refurbishment_measure{}.energy_refurbishment_measure_energy_date_energy_date_of_event_energy_period_gml_time_period_gml_related_time{}.gml_time_node_gml_position_xlink_href xml_buffer, energy_refurbishment_measure{}.energy_refurbishment_measure_energy_date_energy_date_of_event_energy_period_gml_time_period_gml_related_time{}.gml_time_node_gml_position_gml_time_instant_frame xml_buffer, energy_refurbishment_measure{}.energy_refurbishment_measure_energy_date_energy_date_of_event_energy_period_gml_time_period_gml_related_time{}.gml_time_node_gml_position_gml_time_instant_gml_id xml_buffer, energy_refurbishment_measure{}.energy_refurbishment_measure_energy_date_energy_date_of_event_energy_period_gml_time_period_gml_related_time{}.gml_time_node_gml_position_gml_time_instant_gml_related_time{} xml_xml, energy_refurbishment_measure{}.energy_refurbishment_measure_energy_date_energy_date_of_event_energy_period_gml_time_period_gml_related_time{}.gml_time_node_gml_position_gml_time_instant_gml_related_time{}.relativePosition xml_char(12), energy_refurbishment_measure{}.energy_refurbishment_measure_energy_date_energy_date_of_event_energy_period_gml_time_period_gml_related_time{}.gml_time_node_gml_position_gml_time_instant_gml_related_time{}.xlink_href xml_buffer, energy_refurbishment_measure{}.energy_refurbishment_measure_energy_date_energy_date_of_event_energy_period_gml_time_period_gml_related_time{}.gml_time_node_gml_position_gml_time_instant_gml_time_position xml_buffer, energy_refurbishment_measure{}.energy_refurbishment_measure_energy_date_energy_date_of_event_energy_period_gml_time_period_gml_related_time{}.gml_time_node_gml_position_gml_time_instant_gml_time_position_frame xml_buffer, energy_refurbishment_measure{}.energy_refurbishment_measure_energy_date_energy_date_of_event_energy_period_gml_time_period_gml_related_time{}.gml_time_node_gml_position_gml_time_instant_gml_time_position_calendarEraName xml_buffer, energy_refurbishment_measure{}.energy_refurbishment_measure_energy_date_energy_date_of_event_energy_period_gml_time_period_gml_related_time{}.gml_time_node_gml_position_gml_time_instant_gml_time_position_indeterminatePosition xml_char(7), energy_refurbishment_measure{}.energy_refurbishment_measure_energy_date_energy_date_of_event_energy_period_gml_time_period_gml_related_time{}.gml_time_period xml_xml, energy_refurbishment_measure{}.energy_refurbishment_measure_energy_date_energy_date_of_event_energy_period_gml_time_period_gml_related_time{}.gml_time_period_frame xml_buffer, energy_refurbishment_measure{}.energy_refurbishment_measure_energy_date_energy_date_of_event_energy_period_gml_time_period_gml_related_time{}.gml_time_period_gml_id xml_buffer, energy_refurbishment_measure{}.energy_refurbishment_measure_energy_date_energy_date_of_event_energy_period_gml_time_period_gml_begin_position xml_buffer, energy_refurbishment_measure{}.energy_refurbishment_measure_energy_date_energy_date_of_event_energy_period_gml_time_period_gml_begin_position_frame xml_buffer, energy_refurbishment_measure{}.energy_refurbishment_measure_energy_date_energy_date_of_event_energy_period_gml_time_period_gml_begin_position_calendarEraName xml_buffer, energy_refurbishment_measure{}.energy_refurbishment_measure_energy_date_energy_date_of_event_energy_period_gml_time_period_gml_begin_position_indeterminatePosition xml_char(7), energy_refurbishment_measure{}.energy_refurbishment_measure_energy_date_energy_date_of_event_energy_period_gml_time_period_gml_begin_xlink_href xml_buffer,
      energy_refurbishment_measure{}.energy_refurbishment_measure_energy_date_energy_date_of_event_energy_period_gml_time_period_gml_begin_gml_time_instant_frame xml_buffer, energy_refurbishment_measure{}.energy_refurbishment_measure_energy_date_energy_date_of_event_energy_period_gml_time_period_gml_begin_gml_time_instant_gml_id xml_buffer, energy_refurbishment_measure{}.energy_refurbishment_measure_energy_date_energy_date_of_event_energy_period_gml_time_period_gml_begin_gml_time_instant_gml_related_time{}.relativePosition xml_char(12), energy_refurbishment_measure{}.energy_refurbishment_measure_energy_date_energy_date_of_event_energy_period_gml_time_period_gml_begin_gml_time_instant_gml_related_time{}.xlink_href xml_buffer, energy_refurbishment_measure{}.energy_refurbishment_measure_energy_date_energy_date_of_event_energy_period_gml_time_period_gml_begin_gml_time_instant_gml_related_time{}.gml_time_edge_gml_id xml_buffer, energy_refurbishment_measure{}.energy_refurbishment_measure_energy_date_energy_date_of_event_energy_period_gml_time_period_gml_begin_gml_time_instant_gml_related_time{}.gml_time_edge_gml_related_time{} xml_xml, energy_refurbishment_measure{}.energy_refurbishment_measure_energy_date_energy_date_of_event_energy_period_gml_time_period_gml_begin_gml_time_instant_gml_related_time{}.gml_time_edge_gml_related_time{}.relativePosition xml_char(12), energy_refurbishment_measure{}.energy_refurbishment_measure_energy_date_energy_date_of_event_energy_period_gml_time_period_gml_begin_gml_time_instant_gml_related_time{}.gml_time_edge_gml_related_time{}.xlink_href xml_buffer, energy_refurbishment_measure{}.energy_refurbishment_measure_energy_date_energy_date_of_event_energy_period_gml_time_period_gml_begin_gml_time_instant_gml_related_time{}.gml_time_edge_gml_complex_xlink_href xml_buffer, energy_refurbishment_measure{}.energy_refurbishment_measure_energy_date_energy_date_of_event_energy_period_gml_time_period_gml_begin_gml_time_instant_gml_related_time{}.gml_time_edge_gml_start_xlink_href xml_buffer, energy_refurbishment_measure{}.energy_refurbishment_measure_energy_date_energy_date_of_event_energy_period_gml_time_period_gml_begin_gml_time_instant_gml_related_time{}.gml_time_edge_gml_start_gml_time_node_gml_id xml_buffer, energy_refurbishment_measure{}.energy_refurbishment_measure_energy_date_energy_date_of_event_energy_period_gml_time_period_gml_begin_gml_time_instant_gml_related_time{}.gml_time_edge_gml_start_gml_time_node_gml_related_time{} xml_xml, energy_refurbishment_measure{}.energy_refurbishment_measure_energy_date_energy_date_of_event_energy_period_gml_time_period_gml_begin_gml_time_instant_gml_related_time{}.gml_time_edge_gml_start_gml_time_node_gml_related_time{}.relativePosition xml_char(12), energy_refurbishment_measure{}.energy_refurbishment_measure_energy_date_energy_date_of_event_energy_period_gml_time_period_gml_begin_gml_time_instant_gml_related_time{}.gml_time_edge_gml_start_gml_time_node_gml_related_time{}.xlink_href xml_buffer, energy_refurbishment_measure{}.energy_refurbishment_measure_energy_date_energy_date_of_event_energy_period_gml_time_period_gml_begin_gml_time_instant_gml_related_time{}.gml_time_edge_gml_start_gml_time_node_gml_complex_xlink_href xml_buffer, energy_refurbishment_measure{}.energy_refurbishment_measure_energy_date_energy_date_of_event_energy_period_gml_time_period_gml_begin_gml_time_instant_gml_related_time{}.gml_time_edge_gml_start_gml_time_node_gml_previous_edge{}.xlink_href xml_buffer, energy_refurbishment_measure{}.energy_refurbishment_measure_energy_date_energy_date_of_event_energy_period_gml_time_period_gml_begin_gml_time_instant_gml_related_time{}.gml_time_edge_gml_start_gml_time_node_gml_previous_edge{}.gml_time_edge xml_xml, energy_refurbishment_measure{}.energy_refurbishment_measure_energy_date_energy_date_of_event_energy_period_gml_time_period_gml_begin_gml_time_instant_gml_related_time{}.gml_time_edge_gml_start_gml_time_node_gml_previous_edge{}.gml_time_edge_gml_id xml_buffer, energy_refurbishment_measure{}.energy_refurbishment_measure_energy_date_energy_date_of_event_energy_period_gml_time_period_gml_begin_gml_time_instant_gml_related_time{}.gml_time_edge_gml_start_gml_time_node_gml_next_edge{}.xlink_href xml_buffer, energy_refurbishment_measure{}.energy_refurbishment_measure_energy_date_energy_date_of_event_energy_period_gml_time_period_gml_begin_gml_time_instant_gml_related_time{}.gml_time_edge_gml_start_gml_time_node_gml_next_edge{}.gml_time_edge xml_xml, energy_refurbishment_measure{}.energy_refurbishment_measure_energy_date_energy_date_of_event_energy_period_gml_time_period_gml_begin_gml_time_instant_gml_related_time{}.gml_time_edge_gml_start_gml_time_node_gml_next_edge{}.gml_time_edge_gml_id xml_buffer, energy_refurbishment_measure{}.energy_refurbishment_measure_energy_date_energy_date_of_event_energy_period_gml_time_period_gml_begin_gml_time_instant_gml_related_time{}.gml_time_edge_gml_start_gml_time_node_gml_position_xlink_href xml_buffer, energy_refurbishment_measure{}.energy_refurbishment_measure_energy_date_energy_date_of_event_energy_period_gml_time_period_gml_begin_gml_time_instant_gml_related_time{}.gml_time_edge_gml_start_gml_time_node_gml_position_gml_time_instant xml_xml, energy_refurbishment_measure{}.energy_refurbishment_measure_energy_date_energy_date_of_event_energy_period_gml_time_period_gml_begin_gml_time_instant_gml_related_time{}.gml_time_edge_gml_start_gml_time_node_gml_position_gml_time_instant_frame xml_buffer, energy_refurbishment_measure{}.energy_refurbishment_measure_energy_date_energy_date_of_event_energy_period_gml_time_period_gml_begin_gml_time_instant_gml_related_time{}.gml_time_edge_gml_start_gml_time_node_gml_position_gml_time_instant_gml_id xml_buffer, energy_refurbishment_measure{}.energy_refurbishment_measure_energy_date_energy_date_of_event_energy_period_gml_time_period_gml_begin_gml_time_instant_gml_related_time{}.gml_time_edge_gml_end_xlink_href xml_buffer, energy_refurbishment_measure{}.energy_refurbishment_measure_energy_date_energy_date_of_event_energy_period_gml_time_period_gml_begin_gml_time_instant_gml_related_time{}.gml_time_edge_gml_end_gml_time_node_gml_id xml_buffer, energy_refurbishment_measure{}.energy_refurbishment_measure_energy_date_energy_date_of_event_energy_period_gml_time_period_gml_begin_gml_time_instant_gml_related_time{}.gml_time_edge_gml_end_gml_time_node_gml_related_time{} xml_xml, energy_refurbishment_measure{}.energy_refurbishment_measure_energy_date_energy_date_of_event_energy_period_gml_time_period_gml_begin_gml_time_instant_gml_related_time{}.gml_time_edge_gml_end_gml_time_node_gml_related_time{}.relativePosition xml_char(12), energy_refurbishment_measure{}.energy_refurbishment_measure_energy_date_energy_date_of_event_energy_period_gml_time_period_gml_begin_gml_time_instant_gml_related_time{}.gml_time_edge_gml_end_gml_time_node_gml_related_time{}.xlink_href xml_buffer,
      energy_refurbishment_measure{}.energy_refurbishment_measure_energy_date_energy_date_of_event_energy_period_gml_time_period_gml_begin_gml_time_instant_gml_related_time{}.gml_time_edge_gml_end_gml_time_node_gml_complex_xlink_href xml_buffer, energy_refurbishment_measure{}.energy_refurbishment_measure_energy_date_energy_date_of_event_energy_period_gml_time_period_gml_begin_gml_time_instant_gml_related_time{}.gml_time_edge_gml_end_gml_time_node_gml_previous_edge{}.xlink_href xml_buffer, energy_refurbishment_measure{}.energy_refurbishment_measure_energy_date_energy_date_of_event_energy_period_gml_time_period_gml_begin_gml_time_instant_gml_related_time{}.gml_time_edge_gml_end_gml_time_node_gml_previous_edge{}.gml_time_edge xml_xml, energy_refurbishment_measure{}.energy_refurbishment_measure_energy_date_energy_date_of_event_energy_period_gml_time_period_gml_begin_gml_time_instant_gml_related_time{}.gml_time_edge_gml_end_gml_time_node_gml_previous_edge{}.gml_time_edge_gml_id xml_buffer, energy_refurbishment_measure{}.energy_refurbishment_measure_energy_date_energy_date_of_event_energy_period_gml_time_period_gml_begin_gml_time_instant_gml_related_time{}.gml_time_edge_gml_end_gml_time_node_gml_next_edge{}.xlink_href xml_buffer, energy_refurbishment_measure{}.energy_refurbishment_measure_energy_date_energy_date_of_event_energy_period_gml_time_period_gml_begin_gml_time_instant_gml_related_time{}.gml_time_edge_gml_end_gml_time_node_gml_next_edge{}.gml_time_edge xml_xml, energy_refurbishment_measure{}.energy_refurbishment_measure_energy_date_energy_date_of_event_energy_period_gml_time_period_gml_begin_gml_time_instant_gml_related_time{}.gml_time_edge_gml_end_gml_time_node_gml_next_edge{}.gml_time_edge_gml_id xml_buffer, energy_refurbishment_measure{}.energy_refurbishment_measure_energy_date_energy_date_of_event_energy_period_gml_time_period_gml_begin_gml_time_instant_gml_related_time{}.gml_time_edge_gml_end_gml_time_node_gml_position_xlink_href xml_buffer, energy_refurbishment_measure{}.energy_refurbishment_measure_energy_date_energy_date_of_event_energy_period_gml_time_period_gml_begin_gml_time_instant_gml_related_time{}.gml_time_edge_gml_end_gml_time_node_gml_position_gml_time_instant xml_xml, energy_refurbishment_measure{}.energy_refurbishment_measure_energy_date_energy_date_of_event_energy_period_gml_time_period_gml_begin_gml_time_instant_gml_related_time{}.gml_time_edge_gml_end_gml_time_node_gml_position_gml_time_instant_frame xml_buffer, energy_refurbishment_measure{}.energy_refurbishment_measure_energy_date_energy_date_of_event_energy_period_gml_time_period_gml_begin_gml_time_instant_gml_related_time{}.gml_time_edge_gml_end_gml_time_node_gml_position_gml_time_instant_gml_id xml_buffer, energy_refurbishment_measure{}.energy_refurbishment_measure_energy_date_energy_date_of_event_energy_period_gml_time_period_gml_begin_gml_time_instant_gml_related_time{}.gml_time_edge_gml_extent_xlink_href xml_buffer, energy_refurbishment_measure{}.energy_refurbishment_measure_energy_date_energy_date_of_event_energy_period_gml_time_period_gml_begin_gml_time_instant_gml_related_time{}.gml_time_edge_gml_extent_gml_time_period xml_xml, energy_refurbishment_measure{}.energy_refurbishment_measure_energy_date_energy_date_of_event_energy_period_gml_time_period_gml_begin_gml_time_instant_gml_related_time{}.gml_time_edge_gml_extent_gml_time_period_frame xml_buffer, energy_refurbishment_measure{}.energy_refurbishment_measure_energy_date_energy_date_of_event_energy_period_gml_time_period_gml_begin_gml_time_instant_gml_related_time{}.gml_time_edge_gml_extent_gml_time_period_gml_id xml_buffer, energy_refurbishment_measure{}.energy_refurbishment_measure_energy_date_energy_date_of_event_energy_period_gml_time_period_gml_begin_gml_time_instant_gml_related_time{}.gml_time_instant xml_xml, energy_refurbishment_measure{}.energy_refurbishment_measure_energy_date_energy_date_of_event_energy_period_gml_time_period_gml_begin_gml_time_instant_gml_related_time{}.gml_time_instant_frame xml_buffer, energy_refurbishment_measure{}.energy_refurbishment_measure_energy_date_energy_date_of_event_energy_period_gml_time_period_gml_begin_gml_time_instant_gml_related_time{}.gml_time_instant_gml_id xml_buffer, energy_refurbishment_measure{}.energy_refurbishment_measure_energy_date_energy_date_of_event_energy_period_gml_time_period_gml_begin_gml_time_instant_gml_related_time{}.gml_time_node_gml_id xml_buffer, energy_refurbishment_measure{}.energy_refurbishment_measure_energy_date_energy_date_of_event_energy_period_gml_time_period_gml_begin_gml_time_instant_gml_related_time{}.gml_time_node_gml_related_time{} xml_xml, energy_refurbishment_measure{}.energy_refurbishment_measure_energy_date_energy_date_of_event_energy_period_gml_time_period_gml_begin_gml_time_instant_gml_related_time{}.gml_time_node_gml_related_time{}.relativePosition xml_char(12), energy_refurbishment_measure{}.energy_refurbishment_measure_energy_date_energy_date_of_event_energy_period_gml_time_period_gml_begin_gml_time_instant_gml_related_time{}.gml_time_node_gml_related_time{}.xlink_href xml_buffer, energy_refurbishment_measure{}.energy_refurbishment_measure_energy_date_energy_date_of_event_energy_period_gml_time_period_gml_begin_gml_time_instant_gml_related_time{}.gml_time_node_gml_complex_xlink_href xml_buffer, energy_refurbishment_measure{}.energy_refurbishment_measure_energy_date_energy_date_of_event_energy_period_gml_time_period_gml_begin_gml_time_instant_gml_related_time{}.gml_time_node_gml_previous_edge{}.xlink_href xml_buffer, energy_refurbishment_measure{}.energy_refurbishment_measure_energy_date_energy_date_of_event_energy_period_gml_time_period_gml_begin_gml_time_instant_gml_related_time{}.gml_time_node_gml_previous_edge{}.gml_time_edge_gml_id xml_buffer, energy_refurbishment_measure{}.energy_refurbishment_measure_energy_date_energy_date_of_event_energy_period_gml_time_period_gml_begin_gml_time_instant_gml_related_time{}.gml_time_node_gml_previous_edge{}.gml_time_edge_gml_related_time{} xml_xml, energy_refurbishment_measure{}.energy_refurbishment_measure_energy_date_energy_date_of_event_energy_period_gml_time_period_gml_begin_gml_time_instant_gml_related_time{}.gml_time_node_gml_previous_edge{}.gml_time_edge_gml_related_time{}.relativePosition xml_char(12), energy_refurbishment_measure{}.energy_refurbishment_measure_energy_date_energy_date_of_event_energy_period_gml_time_period_gml_begin_gml_time_instant_gml_related_time{}.gml_time_node_gml_previous_edge{}.gml_time_edge_gml_related_time{}.xlink_href xml_buffer, energy_refurbishment_measure{}.energy_refurbishment_measure_energy_date_energy_date_of_event_energy_period_gml_time_period_gml_begin_gml_time_instant_gml_related_time{}.gml_time_node_gml_previous_edge{}.gml_time_edge_gml_complex_xlink_href xml_buffer, energy_refurbishment_measure{}.energy_refurbishment_measure_energy_date_energy_date_of_event_energy_period_gml_time_period_gml_begin_gml_time_instant_gml_related_time{}.gml_time_node_gml_previous_edge{}.gml_time_edge_gml_start_xlink_href xml_buffer,
      energy_refurbishment_measure{}.energy_refurbishment_measure_energy_date_energy_date_of_event_energy_period_gml_time_period_gml_begin_gml_time_instant_gml_related_time{}.gml_time_node_gml_previous_edge{}.gml_time_edge_gml_start_gml_time_node xml_xml, energy_refurbishment_measure{}.energy_refurbishment_measure_energy_date_energy_date_of_event_energy_period_gml_time_period_gml_begin_gml_time_instant_gml_related_time{}.gml_time_node_gml_previous_edge{}.gml_time_edge_gml_start_gml_time_node_gml_id xml_buffer, energy_refurbishment_measure{}.energy_refurbishment_measure_energy_date_energy_date_of_event_energy_period_gml_time_period_gml_begin_gml_time_instant_gml_related_time{}.gml_time_node_gml_previous_edge{}.gml_time_edge_gml_end_xlink_href xml_buffer, energy_refurbishment_measure{}.energy_refurbishment_measure_energy_date_energy_date_of_event_energy_period_gml_time_period_gml_begin_gml_time_instant_gml_related_time{}.gml_time_node_gml_previous_edge{}.gml_time_edge_gml_end_gml_time_node xml_xml, energy_refurbishment_measure{}.energy_refurbishment_measure_energy_date_energy_date_of_event_energy_period_gml_time_period_gml_begin_gml_time_instant_gml_related_time{}.gml_time_node_gml_previous_edge{}.gml_time_edge_gml_end_gml_time_node_gml_id xml_buffer, energy_refurbishment_measure{}.energy_refurbishment_measure_energy_date_energy_date_of_event_energy_period_gml_time_period_gml_begin_gml_time_instant_gml_related_time{}.gml_time_node_gml_previous_edge{}.gml_time_edge_gml_extent_xlink_href xml_buffer, energy_refurbishment_measure{}.energy_refurbishment_measure_energy_date_energy_date_of_event_energy_period_gml_time_period_gml_begin_gml_time_instant_gml_related_time{}.gml_time_node_gml_previous_edge{}.gml_time_edge_gml_extent_gml_time_period xml_xml, energy_refurbishment_measure{}.energy_refurbishment_measure_energy_date_energy_date_of_event_energy_period_gml_time_period_gml_begin_gml_time_instant_gml_related_time{}.gml_time_node_gml_previous_edge{}.gml_time_edge_gml_extent_gml_time_period_frame xml_buffer, energy_refurbishment_measure{}.energy_refurbishment_measure_energy_date_energy_date_of_event_energy_period_gml_time_period_gml_begin_gml_time_instant_gml_related_time{}.gml_time_node_gml_previous_edge{}.gml_time_edge_gml_extent_gml_time_period_gml_id xml_buffer, energy_refurbishment_measure{}.energy_refurbishment_measure_energy_date_energy_date_of_event_energy_period_gml_time_period_gml_begin_gml_time_instant_gml_related_time{}.gml_time_node_gml_next_edge{}.xlink_href xml_buffer, energy_refurbishment_measure{}.energy_refurbishment_measure_energy_date_energy_date_of_event_energy_period_gml_time_period_gml_begin_gml_time_instant_gml_related_time{}.gml_time_node_gml_next_edge{}.gml_time_edge_gml_id xml_buffer, energy_refurbishment_measure{}.energy_refurbishment_measure_energy_date_energy_date_of_event_energy_period_gml_time_period_gml_begin_gml_time_instant_gml_related_time{}.gml_time_node_gml_next_edge{}.gml_time_edge_gml_related_time{} xml_xml, energy_refurbishment_measure{}.energy_refurbishment_measure_energy_date_energy_date_of_event_energy_period_gml_time_period_gml_begin_gml_time_instant_gml_related_time{}.gml_time_node_gml_next_edge{}.gml_time_edge_gml_related_time{}.relativePosition xml_char(12), energy_refurbishment_measure{}.energy_refurbishment_measure_energy_date_energy_date_of_event_energy_period_gml_time_period_gml_begin_gml_time_instant_gml_related_time{}.gml_time_node_gml_next_edge{}.gml_time_edge_gml_related_time{}.xlink_href xml_buffer, energy_refurbishment_measure{}.energy_refurbishment_measure_energy_date_energy_date_of_event_energy_period_gml_time_period_gml_begin_gml_time_instant_gml_related_time{}.gml_time_node_gml_next_edge{}.gml_time_edge_gml_complex_xlink_href xml_buffer, energy_refurbishment_measure{}.energy_refurbishment_measure_energy_date_energy_date_of_event_energy_period_gml_time_period_gml_begin_gml_time_instant_gml_related_time{}.gml_time_node_gml_next_edge{}.gml_time_edge_gml_start_xlink_href xml_buffer, energy_refurbishment_measure{}.energy_refurbishment_measure_energy_date_energy_date_of_event_energy_period_gml_time_period_gml_begin_gml_time_instant_gml_related_time{}.gml_time_node_gml_next_edge{}.gml_time_edge_gml_start_gml_time_node xml_xml, energy_refurbishment_measure{}.energy_refurbishment_measure_energy_date_energy_date_of_event_energy_period_gml_time_period_gml_begin_gml_time_instant_gml_related_time{}.gml_time_node_gml_next_edge{}.gml_time_edge_gml_start_gml_time_node_gml_id xml_buffer, energy_refurbishment_measure{}.energy_refurbishment_measure_energy_date_energy_date_of_event_energy_period_gml_time_period_gml_begin_gml_time_instant_gml_related_time{}.gml_time_node_gml_next_edge{}.gml_time_edge_gml_end_xlink_href xml_buffer, energy_refurbishment_measure{}.energy_refurbishment_measure_energy_date_energy_date_of_event_energy_period_gml_time_period_gml_begin_gml_time_instant_gml_related_time{}.gml_time_node_gml_next_edge{}.gml_time_edge_gml_end_gml_time_node xml_xml, energy_refurbishment_measure{}.energy_refurbishment_measure_energy_date_energy_date_of_event_energy_period_gml_time_period_gml_begin_gml_time_instant_gml_related_time{}.gml_time_node_gml_next_edge{}.gml_time_edge_gml_end_gml_time_node_gml_id xml_buffer, energy_refurbishment_measure{}.energy_refurbishment_measure_energy_date_energy_date_of_event_energy_period_gml_time_period_gml_begin_gml_time_instant_gml_related_time{}.gml_time_node_gml_next_edge{}.gml_time_edge_gml_extent_xlink_href xml_buffer, energy_refurbishment_measure{}.energy_refurbishment_measure_energy_date_energy_date_of_event_energy_period_gml_time_period_gml_begin_gml_time_instant_gml_related_time{}.gml_time_node_gml_next_edge{}.gml_time_edge_gml_extent_gml_time_period xml_xml, energy_refurbishment_measure{}.energy_refurbishment_measure_energy_date_energy_date_of_event_energy_period_gml_time_period_gml_begin_gml_time_instant_gml_related_time{}.gml_time_node_gml_next_edge{}.gml_time_edge_gml_extent_gml_time_period_frame xml_buffer, energy_refurbishment_measure{}.energy_refurbishment_measure_energy_date_energy_date_of_event_energy_period_gml_time_period_gml_begin_gml_time_instant_gml_related_time{}.gml_time_node_gml_next_edge{}.gml_time_edge_gml_extent_gml_time_period_gml_id xml_buffer, energy_refurbishment_measure{}.energy_refurbishment_measure_energy_date_energy_date_of_event_energy_period_gml_time_period_gml_begin_gml_time_instant_gml_related_time{}.gml_time_node_gml_position_xlink_href xml_buffer, energy_refurbishment_measure{}.energy_refurbishment_measure_energy_date_energy_date_of_event_energy_period_gml_time_period_gml_begin_gml_time_instant_gml_related_time{}.gml_time_node_gml_position_gml_time_instant xml_xml, energy_refurbishment_measure{}.energy_refurbishment_measure_energy_date_energy_date_of_event_energy_period_gml_time_period_gml_begin_gml_time_instant_gml_related_time{}.gml_time_node_gml_position_gml_time_instant_frame xml_buffer, energy_refurbishment_measure{}.energy_refurbishment_measure_energy_date_energy_date_of_event_energy_period_gml_time_period_gml_begin_gml_time_instant_gml_related_time{}.gml_time_node_gml_position_gml_time_instant_gml_id xml_buffer, energy_refurbishment_measure{}.energy_refurbishment_measure_energy_date_energy_date_of_event_energy_period_gml_time_period_gml_begin_gml_time_instant_gml_related_time{}.gml_time_period xml_xml,
      energy_refurbishment_measure{}.energy_refurbishment_measure_energy_date_energy_date_of_event_energy_period_gml_time_period_gml_begin_gml_time_instant_gml_related_time{}.gml_time_period_frame xml_buffer, energy_refurbishment_measure{}.energy_refurbishment_measure_energy_date_energy_date_of_event_energy_period_gml_time_period_gml_begin_gml_time_instant_gml_related_time{}.gml_time_period_gml_id xml_buffer, energy_refurbishment_measure{}.energy_refurbishment_measure_energy_date_energy_date_of_event_energy_period_gml_time_period_gml_begin_gml_time_instant_gml_time_position xml_buffer, energy_refurbishment_measure{}.energy_refurbishment_measure_energy_date_energy_date_of_event_energy_period_gml_time_period_gml_begin_gml_time_instant_gml_time_position_frame xml_buffer, energy_refurbishment_measure{}.energy_refurbishment_measure_energy_date_energy_date_of_event_energy_period_gml_time_period_gml_begin_gml_time_instant_gml_time_position_calendarEraName xml_buffer, energy_refurbishment_measure{}.energy_refurbishment_measure_energy_date_energy_date_of_event_energy_period_gml_time_period_gml_begin_gml_time_instant_gml_time_position_indeterminatePosition xml_char(7), energy_refurbishment_measure{}.energy_refurbishment_measure_energy_date_energy_date_of_event_energy_period_gml_time_period_gml_end_position xml_buffer, energy_refurbishment_measure{}.energy_refurbishment_measure_energy_date_energy_date_of_event_energy_period_gml_time_period_gml_end_position_frame xml_buffer, energy_refurbishment_measure{}.energy_refurbishment_measure_energy_date_energy_date_of_event_energy_period_gml_time_period_gml_end_position_calendarEraName xml_buffer, energy_refurbishment_measure{}.energy_refurbishment_measure_energy_date_energy_date_of_event_energy_period_gml_time_period_gml_end_position_indeterminatePosition xml_char(7), energy_refurbishment_measure{}.energy_refurbishment_measure_energy_date_energy_date_of_event_energy_period_gml_time_period_gml_end_xlink_href xml_buffer, energy_refurbishment_measure{}.energy_refurbishment_measure_energy_date_energy_date_of_event_energy_period_gml_time_period_gml_end_gml_time_instant_frame xml_buffer, energy_refurbishment_measure{}.energy_refurbishment_measure_energy_date_energy_date_of_event_energy_period_gml_time_period_gml_end_gml_time_instant_gml_id xml_buffer, energy_refurbishment_measure{}.energy_refurbishment_measure_energy_date_energy_date_of_event_energy_period_gml_time_period_gml_end_gml_time_instant_gml_related_time{}.relativePosition xml_char(12), energy_refurbishment_measure{}.energy_refurbishment_measure_energy_date_energy_date_of_event_energy_period_gml_time_period_gml_end_gml_time_instant_gml_related_time{}.xlink_href xml_buffer, energy_refurbishment_measure{}.energy_refurbishment_measure_energy_date_energy_date_of_event_energy_period_gml_time_period_gml_end_gml_time_instant_gml_related_time{}.gml_time_edge_gml_id xml_buffer, energy_refurbishment_measure{}.energy_refurbishment_measure_energy_date_energy_date_of_event_energy_period_gml_time_period_gml_end_gml_time_instant_gml_related_time{}.gml_time_edge_gml_related_time{} xml_xml, energy_refurbishment_measure{}.energy_refurbishment_measure_energy_date_energy_date_of_event_energy_period_gml_time_period_gml_end_gml_time_instant_gml_related_time{}.gml_time_edge_gml_related_time{}.relativePosition xml_char(12), energy_refurbishment_measure{}.energy_refurbishment_measure_energy_date_energy_date_of_event_energy_period_gml_time_period_gml_end_gml_time_instant_gml_related_time{}.gml_time_edge_gml_related_time{}.xlink_href xml_buffer, energy_refurbishment_measure{}.energy_refurbishment_measure_energy_date_energy_date_of_event_energy_period_gml_time_period_gml_end_gml_time_instant_gml_related_time{}.gml_time_edge_gml_complex_xlink_href xml_buffer, energy_refurbishment_measure{}.energy_refurbishment_measure_energy_date_energy_date_of_event_energy_period_gml_time_period_gml_end_gml_time_instant_gml_related_time{}.gml_time_edge_gml_start_xlink_href xml_buffer, energy_refurbishment_measure{}.energy_refurbishment_measure_energy_date_energy_date_of_event_energy_period_gml_time_period_gml_end_gml_time_instant_gml_related_time{}.gml_time_edge_gml_start_gml_time_node_gml_id xml_buffer, energy_refurbishment_measure{}.energy_refurbishment_measure_energy_date_energy_date_of_event_energy_period_gml_time_period_gml_end_gml_time_instant_gml_related_time{}.gml_time_edge_gml_start_gml_time_node_gml_related_time{} xml_xml, energy_refurbishment_measure{}.energy_refurbishment_measure_energy_date_energy_date_of_event_energy_period_gml_time_period_gml_end_gml_time_instant_gml_related_time{}.gml_time_edge_gml_start_gml_time_node_gml_related_time{}.relativePosition xml_char(12), energy_refurbishment_measure{}.energy_refurbishment_measure_energy_date_energy_date_of_event_energy_period_gml_time_period_gml_end_gml_time_instant_gml_related_time{}.gml_time_edge_gml_start_gml_time_node_gml_related_time{}.xlink_href xml_buffer, energy_refurbishment_measure{}.energy_refurbishment_measure_energy_date_energy_date_of_event_energy_period_gml_time_period_gml_end_gml_time_instant_gml_related_time{}.gml_time_edge_gml_start_gml_time_node_gml_complex_xlink_href xml_buffer, energy_refurbishment_measure{}.energy_refurbishment_measure_energy_date_energy_date_of_event_energy_period_gml_time_period_gml_end_gml_time_instant_gml_related_time{}.gml_time_edge_gml_start_gml_time_node_gml_previous_edge{}.xlink_href xml_buffer, energy_refurbishment_measure{}.energy_refurbishment_measure_energy_date_energy_date_of_event_energy_period_gml_time_period_gml_end_gml_time_instant_gml_related_time{}.gml_time_edge_gml_start_gml_time_node_gml_previous_edge{}.gml_time_edge xml_xml, energy_refurbishment_measure{}.energy_refurbishment_measure_energy_date_energy_date_of_event_energy_period_gml_time_period_gml_end_gml_time_instant_gml_related_time{}.gml_time_edge_gml_start_gml_time_node_gml_previous_edge{}.gml_time_edge_gml_id xml_buffer, energy_refurbishment_measure{}.energy_refurbishment_measure_energy_date_energy_date_of_event_energy_period_gml_time_period_gml_end_gml_time_instant_gml_related_time{}.gml_time_edge_gml_start_gml_time_node_gml_next_edge{}.xlink_href xml_buffer,
      energy_refurbishment_measure{}.energy_refurbishment_measure_energy_date_energy_date_of_event_energy_period_gml_time_period_gml_end_gml_time_instant_gml_related_time{}.gml_time_edge_gml_start_gml_time_node_gml_next_edge{}.gml_time_edge xml_xml, energy_refurbishment_measure{}.energy_refurbishment_measure_energy_date_energy_date_of_event_energy_period_gml_time_period_gml_end_gml_time_instant_gml_related_time{}.gml_time_edge_gml_start_gml_time_node_gml_next_edge{}.gml_time_edge_gml_id xml_buffer, energy_refurbishment_measure{}.energy_refurbishment_measure_energy_date_energy_date_of_event_energy_period_gml_time_period_gml_end_gml_time_instant_gml_related_time{}.gml_time_edge_gml_start_gml_time_node_gml_position_xlink_href xml_buffer, energy_refurbishment_measure{}.energy_refurbishment_measure_energy_date_energy_date_of_event_energy_period_gml_time_period_gml_end_gml_time_instant_gml_related_time{}.gml_time_edge_gml_start_gml_time_node_gml_position_gml_time_instant xml_xml, energy_refurbishment_measure{}.energy_refurbishment_measure_energy_date_energy_date_of_event_energy_period_gml_time_period_gml_end_gml_time_instant_gml_related_time{}.gml_time_edge_gml_start_gml_time_node_gml_position_gml_time_instant_frame xml_buffer, energy_refurbishment_measure{}.energy_refurbishment_measure_energy_date_energy_date_of_event_energy_period_gml_time_period_gml_end_gml_time_instant_gml_related_time{}.gml_time_edge_gml_start_gml_time_node_gml_position_gml_time_instant_gml_id xml_buffer, energy_refurbishment_measure{}.energy_refurbishment_measure_energy_date_energy_date_of_event_energy_period_gml_time_period_gml_end_gml_time_instant_gml_related_time{}.gml_time_edge_gml_end_xlink_href xml_buffer, energy_refurbishment_measure{}.energy_refurbishment_measure_energy_date_energy_date_of_event_energy_period_gml_time_period_gml_end_gml_time_instant_gml_related_time{}.gml_time_edge_gml_end_gml_time_node_gml_id xml_buffer, energy_refurbishment_measure{}.energy_refurbishment_measure_energy_date_energy_date_of_event_energy_period_gml_time_period_gml_end_gml_time_instant_gml_related_time{}.gml_time_edge_gml_end_gml_time_node_gml_related_time{} xml_xml, energy_refurbishment_measure{}.energy_refurbishment_measure_energy_date_energy_date_of_event_energy_period_gml_time_period_gml_end_gml_time_instant_gml_related_time{}.gml_time_edge_gml_end_gml_time_node_gml_related_time{}.relativePosition xml_char(12), energy_refurbishment_measure{}.energy_refurbishment_measure_energy_date_energy_date_of_event_energy_period_gml_time_period_gml_end_gml_time_instant_gml_related_time{}.gml_time_edge_gml_end_gml_time_node_gml_related_time{}.xlink_href xml_buffer, energy_refurbishment_measure{}.energy_refurbishment_measure_energy_date_energy_date_of_event_energy_period_gml_time_period_gml_end_gml_time_instant_gml_related_time{}.gml_time_edge_gml_end_gml_time_node_gml_complex_xlink_href xml_buffer, energy_refurbishment_measure{}.energy_refurbishment_measure_energy_date_energy_date_of_event_energy_period_gml_time_period_gml_end_gml_time_instant_gml_related_time{}.gml_time_edge_gml_end_gml_time_node_gml_previous_edge{}.xlink_href xml_buffer, energy_refurbishment_measure{}.energy_refurbishment_measure_energy_date_energy_date_of_event_energy_period_gml_time_period_gml_end_gml_time_instant_gml_related_time{}.gml_time_edge_gml_end_gml_time_node_gml_previous_edge{}.gml_time_edge xml_xml, energy_refurbishment_measure{}.energy_refurbishment_measure_energy_date_energy_date_of_event_energy_period_gml_time_period_gml_end_gml_time_instant_gml_related_time{}.gml_time_edge_gml_end_gml_time_node_gml_previous_edge{}.gml_time_edge_gml_id xml_buffer, energy_refurbishment_measure{}.energy_refurbishment_measure_energy_date_energy_date_of_event_energy_period_gml_time_period_gml_end_gml_time_instant_gml_related_time{}.gml_time_edge_gml_end_gml_time_node_gml_next_edge{}.xlink_href xml_buffer, energy_refurbishment_measure{}.energy_refurbishment_measure_energy_date_energy_date_of_event_energy_period_gml_time_period_gml_end_gml_time_instant_gml_related_time{}.gml_time_edge_gml_end_gml_time_node_gml_next_edge{}.gml_time_edge xml_xml, energy_refurbishment_measure{}.energy_refurbishment_measure_energy_date_energy_date_of_event_energy_period_gml_time_period_gml_end_gml_time_instant_gml_related_time{}.gml_time_edge_gml_end_gml_time_node_gml_next_edge{}.gml_time_edge_gml_id xml_buffer, energy_refurbishment_measure{}.energy_refurbishment_measure_energy_date_energy_date_of_event_energy_period_gml_time_period_gml_end_gml_time_instant_gml_related_time{}.gml_time_edge_gml_end_gml_time_node_gml_position_xlink_href xml_buffer, energy_refurbishment_measure{}.energy_refurbishment_measure_energy_date_energy_date_of_event_energy_period_gml_time_period_gml_end_gml_time_instant_gml_related_time{}.gml_time_edge_gml_end_gml_time_node_gml_position_gml_time_instant xml_xml, energy_refurbishment_measure{}.energy_refurbishment_measure_energy_date_energy_date_of_event_energy_period_gml_time_period_gml_end_gml_time_instant_gml_related_time{}.gml_time_edge_gml_end_gml_time_node_gml_position_gml_time_instant_frame xml_buffer, energy_refurbishment_measure{}.energy_refurbishment_measure_energy_date_energy_date_of_event_energy_period_gml_time_period_gml_end_gml_time_instant_gml_related_time{}.gml_time_edge_gml_end_gml_time_node_gml_position_gml_time_instant_gml_id xml_buffer, energy_refurbishment_measure{}.energy_refurbishment_measure_energy_date_energy_date_of_event_energy_period_gml_time_period_gml_end_gml_time_instant_gml_related_time{}.gml_time_edge_gml_extent_xlink_href xml_buffer, energy_refurbishment_measure{}.energy_refurbishment_measure_energy_date_energy_date_of_event_energy_period_gml_time_period_gml_end_gml_time_instant_gml_related_time{}.gml_time_edge_gml_extent_gml_time_period xml_xml, energy_refurbishment_measure{}.energy_refurbishment_measure_energy_date_energy_date_of_event_energy_period_gml_time_period_gml_end_gml_time_instant_gml_related_time{}.gml_time_edge_gml_extent_gml_time_period_frame xml_buffer, energy_refurbishment_measure{}.energy_refurbishment_measure_energy_date_energy_date_of_event_energy_period_gml_time_period_gml_end_gml_time_instant_gml_related_time{}.gml_time_edge_gml_extent_gml_time_period_gml_id xml_buffer, energy_refurbishment_measure{}.energy_refurbishment_measure_energy_date_energy_date_of_event_energy_period_gml_time_period_gml_end_gml_time_instant_gml_related_time{}.gml_time_instant xml_xml, energy_refurbishment_measure{}.energy_refurbishment_measure_energy_date_energy_date_of_event_energy_period_gml_time_period_gml_end_gml_time_instant_gml_related_time{}.gml_time_instant_frame xml_buffer, energy_refurbishment_measure{}.energy_refurbishment_measure_energy_date_energy_date_of_event_energy_period_gml_time_period_gml_end_gml_time_instant_gml_related_time{}.gml_time_instant_gml_id xml_buffer, energy_refurbishment_measure{}.energy_refurbishment_measure_energy_date_energy_date_of_event_energy_period_gml_time_period_gml_end_gml_time_instant_gml_related_time{}.gml_time_node_gml_id xml_buffer,
      energy_refurbishment_measure{}.energy_refurbishment_measure_energy_date_energy_date_of_event_energy_period_gml_time_period_gml_end_gml_time_instant_gml_related_time{}.gml_time_node_gml_related_time{} xml_xml, energy_refurbishment_measure{}.energy_refurbishment_measure_energy_date_energy_date_of_event_energy_period_gml_time_period_gml_end_gml_time_instant_gml_related_time{}.gml_time_node_gml_related_time{}.relativePosition xml_char(12), energy_refurbishment_measure{}.energy_refurbishment_measure_energy_date_energy_date_of_event_energy_period_gml_time_period_gml_end_gml_time_instant_gml_related_time{}.gml_time_node_gml_related_time{}.xlink_href xml_buffer, energy_refurbishment_measure{}.energy_refurbishment_measure_energy_date_energy_date_of_event_energy_period_gml_time_period_gml_end_gml_time_instant_gml_related_time{}.gml_time_node_gml_complex_xlink_href xml_buffer, energy_refurbishment_measure{}.energy_refurbishment_measure_energy_date_energy_date_of_event_energy_period_gml_time_period_gml_end_gml_time_instant_gml_related_time{}.gml_time_node_gml_previous_edge{}.xlink_href xml_buffer, energy_refurbishment_measure{}.energy_refurbishment_measure_energy_date_energy_date_of_event_energy_period_gml_time_period_gml_end_gml_time_instant_gml_related_time{}.gml_time_node_gml_previous_edge{}.gml_time_edge_gml_id xml_buffer, energy_refurbishment_measure{}.energy_refurbishment_measure_energy_date_energy_date_of_event_energy_period_gml_time_period_gml_end_gml_time_instant_gml_related_time{}.gml_time_node_gml_previous_edge{}.gml_time_edge_gml_related_time{} xml_xml, energy_refurbishment_measure{}.energy_refurbishment_measure_energy_date_energy_date_of_event_energy_period_gml_time_period_gml_end_gml_time_instant_gml_related_time{}.gml_time_node_gml_previous_edge{}.gml_time_edge_gml_related_time{}.relativePosition xml_char(12), energy_refurbishment_measure{}.energy_refurbishment_measure_energy_date_energy_date_of_event_energy_period_gml_time_period_gml_end_gml_time_instant_gml_related_time{}.gml_time_node_gml_previous_edge{}.gml_time_edge_gml_related_time{}.xlink_href xml_buffer, energy_refurbishment_measure{}.energy_refurbishment_measure_energy_date_energy_date_of_event_energy_period_gml_time_period_gml_end_gml_time_instant_gml_related_time{}.gml_time_node_gml_previous_edge{}.gml_time_edge_gml_complex_xlink_href xml_buffer, energy_refurbishment_measure{}.energy_refurbishment_measure_energy_date_energy_date_of_event_energy_period_gml_time_period_gml_end_gml_time_instant_gml_related_time{}.gml_time_node_gml_previous_edge{}.gml_time_edge_gml_start_xlink_href xml_buffer, energy_refurbishment_measure{}.energy_refurbishment_measure_energy_date_energy_date_of_event_energy_period_gml_time_period_gml_end_gml_time_instant_gml_related_time{}.gml_time_node_gml_previous_edge{}.gml_time_edge_gml_start_gml_time_node xml_xml, energy_refurbishment_measure{}.energy_refurbishment_measure_energy_date_energy_date_of_event_energy_period_gml_time_period_gml_end_gml_time_instant_gml_related_time{}.gml_time_node_gml_previous_edge{}.gml_time_edge_gml_start_gml_time_node_gml_id xml_buffer, energy_refurbishment_measure{}.energy_refurbishment_measure_energy_date_energy_date_of_event_energy_period_gml_time_period_gml_end_gml_time_instant_gml_related_time{}.gml_time_node_gml_previous_edge{}.gml_time_edge_gml_end_xlink_href xml_buffer, energy_refurbishment_measure{}.energy_refurbishment_measure_energy_date_energy_date_of_event_energy_period_gml_time_period_gml_end_gml_time_instant_gml_related_time{}.gml_time_node_gml_previous_edge{}.gml_time_edge_gml_end_gml_time_node xml_xml, energy_refurbishment_measure{}.energy_refurbishment_measure_energy_date_energy_date_of_event_energy_period_gml_time_period_gml_end_gml_time_instant_gml_related_time{}.gml_time_node_gml_previous_edge{}.gml_time_edge_gml_end_gml_time_node_gml_id xml_buffer, energy_refurbishment_measure{}.energy_refurbishment_measure_energy_date_energy_date_of_event_energy_period_gml_time_period_gml_end_gml_time_instant_gml_related_time{}.gml_time_node_gml_previous_edge{}.gml_time_edge_gml_extent_xlink_href xml_buffer, energy_refurbishment_measure{}.energy_refurbishment_measure_energy_date_energy_date_of_event_energy_period_gml_time_period_gml_end_gml_time_instant_gml_related_time{}.gml_time_node_gml_previous_edge{}.gml_time_edge_gml_extent_gml_time_period xml_xml, energy_refurbishment_measure{}.energy_refurbishment_measure_energy_date_energy_date_of_event_energy_period_gml_time_period_gml_end_gml_time_instant_gml_related_time{}.gml_time_node_gml_previous_edge{}.gml_time_edge_gml_extent_gml_time_period_frame xml_buffer, energy_refurbishment_measure{}.energy_refurbishment_measure_energy_date_energy_date_of_event_energy_period_gml_time_period_gml_end_gml_time_instant_gml_related_time{}.gml_time_node_gml_previous_edge{}.gml_time_edge_gml_extent_gml_time_period_gml_id xml_buffer, energy_refurbishment_measure{}.energy_refurbishment_measure_energy_date_energy_date_of_event_energy_period_gml_time_period_gml_end_gml_time_instant_gml_related_time{}.gml_time_node_gml_next_edge{}.xlink_href xml_buffer, energy_refurbishment_measure{}.energy_refurbishment_measure_energy_date_energy_date_of_event_energy_period_gml_time_period_gml_end_gml_time_instant_gml_related_time{}.gml_time_node_gml_next_edge{}.gml_time_edge_gml_id xml_buffer, gml_description xml_buffer, gml_name xml_buffer, energy_refurbishment_measure{}.energy_refurbishment_measure_energy_date_energy_date_of_event_energy_period_gml_time_period_gml_end_gml_time_instant_gml_related_time{}.gml_time_node_gml_next_edge{}.gml_time_edge_gml_related_time{} xml_xml, energy_refurbishment_measure{}.energy_refurbishment_measure_energy_date_energy_date_of_event_energy_period_gml_time_period_gml_end_gml_time_instant_gml_related_time{}.gml_time_node_gml_next_edge{}.gml_time_edge_gml_related_time{}.relativePosition xml_char(12), energy_refurbishment_measure{}.energy_refurbishment_measure_energy_date_energy_date_of_event_energy_period_gml_time_period_gml_end_gml_time_instant_gml_related_time{}.gml_time_node_gml_next_edge{}.gml_time_edge_gml_related_time{}.xlink_href xml_buffer, energy_refurbishment_measure{}.energy_refurbishment_measure_energy_date_energy_date_of_event_energy_period_gml_time_period_gml_end_gml_time_instant_gml_related_time{}.gml_time_node_gml_next_edge{}.gml_time_edge_gml_complex_xlink_href xml_buffer, energy_refurbishment_measure{}.energy_refurbishment_measure_energy_date_energy_date_of_event_energy_period_gml_time_period_gml_end_gml_time_instant_gml_related_time{}.gml_time_node_gml_next_edge{}.gml_time_edge_gml_start_xlink_href xml_buffer, energy_refurbishment_measure{}.energy_refurbishment_measure_energy_date_energy_date_of_event_energy_period_gml_time_period_gml_end_gml_time_instant_gml_related_time{}.gml_time_node_gml_next_edge{}.gml_time_edge_gml_start_gml_time_node xml_xml,
      energy_refurbishment_measure{}.energy_refurbishment_measure_energy_date_energy_date_of_event_energy_period_gml_time_period_gml_end_gml_time_instant_gml_related_time{}.gml_time_node_gml_next_edge{}.gml_time_edge_gml_start_gml_time_node_gml_id xml_buffer, energy_refurbishment_measure{}.energy_refurbishment_measure_energy_date_energy_date_of_event_energy_period_gml_time_period_gml_end_gml_time_instant_gml_related_time{}.gml_time_node_gml_next_edge{}.gml_time_edge_gml_end_xlink_href xml_buffer, energy_refurbishment_measure{}.energy_refurbishment_measure_energy_date_energy_date_of_event_energy_period_gml_time_period_gml_end_gml_time_instant_gml_related_time{}.gml_time_node_gml_next_edge{}.gml_time_edge_gml_end_gml_time_node xml_xml, energy_refurbishment_measure{}.energy_refurbishment_measure_energy_date_energy_date_of_event_energy_period_gml_time_period_gml_end_gml_time_instant_gml_related_time{}.gml_time_node_gml_next_edge{}.gml_time_edge_gml_end_gml_time_node_gml_id xml_buffer, energy_refurbishment_measure{}.energy_refurbishment_measure_energy_date_energy_date_of_event_energy_period_gml_time_period_gml_end_gml_time_instant_gml_related_time{}.gml_time_node_gml_next_edge{}.gml_time_edge_gml_extent_xlink_href xml_buffer, energy_refurbishment_measure{}.energy_refurbishment_measure_energy_date_energy_date_of_event_energy_period_gml_time_period_gml_end_gml_time_instant_gml_related_time{}.gml_time_node_gml_next_edge{}.gml_time_edge_gml_extent_gml_time_period xml_xml, energy_refurbishment_measure{}.energy_refurbishment_measure_energy_date_energy_date_of_event_energy_period_gml_time_period_gml_end_gml_time_instant_gml_related_time{}.gml_time_node_gml_next_edge{}.gml_time_edge_gml_extent_gml_time_period_frame xml_buffer, energy_refurbishment_measure{}.energy_refurbishment_measure_energy_date_energy_date_of_event_energy_period_gml_time_period_gml_end_gml_time_instant_gml_related_time{}.gml_time_node_gml_next_edge{}.gml_time_edge_gml_extent_gml_time_period_gml_id xml_buffer, energy_refurbishment_measure{}.energy_refurbishment_measure_energy_date_energy_date_of_event_energy_period_gml_time_period_gml_end_gml_time_instant_gml_related_time{}.gml_time_node_gml_position_xlink_href xml_buffer, energy_refurbishment_measure{}.energy_refurbishment_measure_energy_date_energy_date_of_event_energy_period_gml_time_period_gml_end_gml_time_instant_gml_related_time{}.gml_time_node_gml_position_gml_time_instant xml_xml, energy_refurbishment_measure{}.energy_refurbishment_measure_energy_date_energy_date_of_event_energy_period_gml_time_period_gml_end_gml_time_instant_gml_related_time{}.gml_time_node_gml_position_gml_time_instant_frame xml_buffer, energy_refurbishment_measure{}.energy_refurbishment_measure_energy_date_energy_date_of_event_energy_period_gml_time_period_gml_end_gml_time_instant_gml_related_time{}.gml_time_node_gml_position_gml_time_instant_gml_id xml_buffer, energy_refurbishment_measure{}.energy_refurbishment_measure_energy_date_energy_date_of_event_energy_period_gml_time_period_gml_end_gml_time_instant_gml_related_time{}.gml_time_period xml_xml, energy_refurbishment_measure{}.energy_refurbishment_measure_energy_date_energy_date_of_event_energy_period_gml_time_period_gml_end_gml_time_instant_gml_related_time{}.gml_time_period_frame xml_buffer, energy_refurbishment_measure{}.energy_refurbishment_measure_energy_date_energy_date_of_event_energy_period_gml_time_period_gml_end_gml_time_instant_gml_related_time{}.gml_time_period_gml_id xml_buffer, energy_refurbishment_measure{}.energy_refurbishment_measure_energy_date_energy_date_of_event_energy_period_gml_time_period_gml_end_gml_time_instant_gml_time_position xml_buffer, energy_refurbishment_measure{}.energy_refurbishment_measure_energy_date_energy_date_of_event_energy_period_gml_time_period_gml_end_gml_time_instant_gml_time_position_frame xml_buffer, energy_refurbishment_measure{}.energy_refurbishment_measure_energy_date_energy_date_of_event_energy_period_gml_time_period_gml_end_gml_time_instant_gml_time_position_calendarEraName xml_buffer, energy_refurbishment_measure{}.energy_refurbishment_measure_energy_date_energy_date_of_event_energy_period_gml_time_period_gml_end_gml_time_instant_gml_time_position_indeterminatePosition xml_char(7), energy_refurbishment_measure{}.energy_refurbishment_measure_energy_date_energy_date_of_event_energy_period_gml_time_period_gml_duration xml_buffer, energy_refurbishment_measure{}.energy_refurbishment_measure_energy_date_energy_date_of_event_energy_period_gml_time_period_gml_time_interval xml_real64, energy_refurbishment_measure{}.energy_refurbishment_measure_energy_date_energy_date_of_event_energy_period_gml_time_period_gml_time_interval_unit xml_buffer, energy_refurbishment_measure{}.energy_refurbishment_measure_energy_date_energy_date_of_event_energy_period_gml_time_period_gml_time_interval_radix xml_uint64, energy_refurbishment_measure{}.energy_refurbishment_measure_energy_date_energy_date_of_event_energy_period_gml_time_period_gml_time_interval_factor xml_int64, energy_refurbishment_measure{}.energy_refurbishment_measure_energy_level xml_buffer, energy_refurbishment_measure{}.energy_refurbishment_measure_energy_level_codeSpace xml_buffer, energy_refurbishment_measure{}.energy_refurbishment_measure_energy_description xml_buffer, energy_construction_xlink_href xml_buffer, energy_contains{}.xlink_href xml_buffer, energy_delimits{}.xlink_href xml_buffer,
      energy_relates_to{}.xlink_href xml_buffer
ThermalStorageSystem (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_stores{}.xlink_href xml_buffer, energy_preparation_temperature xml_real64, energy_preparation_temperature_units xml_buffer, energy_medium xml_char(5), energy_thermal_losses_factor xml_real64, energy_thermal_losses_factor_units xml_buffer, energy_volume xml_real64, energy_volume_units xml_buffer
    -> AttributeManager_25
ThermalZone (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_contains{}.xlink_href xml_buffer, energy_additional_thermal_bridge_uvalue xml_real64, energy_additional_thermal_bridge_uvalue_units xml_buffer, energy_effective_thermal_capacity xml_real64, energy_effective_thermal_capacity_units xml_buffer, energy_floor_area{}.energy_floor_area_energy_type xml_char(19), energy_floor_area{}.energy_floor_area_energy_value xml_real64, energy_floor_area{}.energy_floor_area_energy_value_units xml_buffer, energy_volume{}.energy_volume_type_energy_type xml_char(21), energy_volume{}.energy_volume_type_energy_value xml_real64, energy_volume{}.energy_volume_type_energy_value_units xml_buffer, energy_indirectly_heated_area_ratio xml_real64,
      energy_indirectly_heated_area_ratio_units xml_buffer, energy_infiltration_rate xml_real64, energy_infiltration_rate_units xml_buffer, energy_is_cooled xml_boolean, energy_is_heated xml_boolean, citygml_level_of_detail{} xml_buffer, energy_interior_room{}.xlink_href xml_buffer, energy_bounded_by{}.xlink_href xml_buffer
    -> ThermalZone (writer CITYGML_2)
ThermalZone (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_contains{}.xlink_href xml_buffer, energy_additional_thermal_bridge_uvalue xml_real64, energy_additional_thermal_bridge_uvalue_units xml_buffer, energy_effective_thermal_capacity xml_real64, energy_effective_thermal_capacity_units xml_buffer, energy_floor_area{}.energy_floor_area_energy_type xml_char(19), energy_floor_area{}.energy_floor_area_energy_value xml_real64, energy_floor_area{}.energy_floor_area_energy_value_units xml_buffer, energy_volume{}.energy_volume_type_energy_type xml_char(21), energy_volume{}.energy_volume_type_energy_value xml_real64, energy_volume{}.energy_volume_type_energy_value_units xml_buffer, energy_indirectly_heated_area_ratio xml_real64,
      energy_indirectly_heated_area_ratio_units xml_buffer, energy_infiltration_rate xml_real64, energy_infiltration_rate_units xml_buffer, energy_is_cooled xml_boolean, energy_is_heated xml_boolean, citygml_level_of_detail{} xml_buffer, energy_interior_room{}.xlink_href xml_buffer, energy_bounded_by{}.xlink_href xml_buffer
UsageZone (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_cooling_schedule xml_xml, energy_cooling_schedule_xlink_href xml_buffer, energy_heating_schedule xml_xml, energy_heating_schedule_xlink_href xml_buffer, energy_usage_zone_type xml_buffer, energy_usage_zone_type_codeSpace xml_buffer, energy_used_floors xml_buffer, energy_ventilation_schedule xml_xml, energy_ventilation_schedule_xlink_href xml_buffer, energy_floor_area{}.energy_floor_area_energy_type xml_char(19), energy_floor_area{}.energy_floor_area_energy_value xml_real64, energy_floor_area{}.energy_floor_area_energy_value_units xml_buffer,
      citygml_level_of_detail{} xml_buffer, energy_average_internal_gains_energy_heat_exchange_type_energy_convective_fraction xml_real64, energy_average_internal_gains_energy_heat_exchange_type_energy_convective_fraction_units xml_buffer, energy_average_internal_gains_energy_heat_exchange_type_energy_latent_fraction xml_real64, energy_average_internal_gains_energy_heat_exchange_type_energy_latent_fraction_units xml_buffer, energy_average_internal_gains_energy_heat_exchange_type_energy_radiant_fraction xml_real64, energy_average_internal_gains_energy_heat_exchange_type_energy_radiant_fraction_units xml_buffer, energy_average_internal_gains_energy_heat_exchange_type_energy_total_value xml_real64, energy_average_internal_gains_energy_heat_exchange_type_energy_total_value_units xml_buffer, energy_contains{}.xlink_href xml_buffer, energy_occupied_by{}.xlink_href xml_buffer, energy_equipped_with{}.xlink_href xml_buffer
    -> UsageZone (writer CITYGML_2)
UsageZone (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_cooling_schedule xml_xml, energy_cooling_schedule_xlink_href xml_buffer, energy_heating_schedule xml_xml, energy_heating_schedule_xlink_href xml_buffer, energy_usage_zone_type xml_buffer, energy_usage_zone_type_codeSpace xml_buffer, energy_used_floors xml_buffer, energy_ventilation_schedule xml_xml, energy_ventilation_schedule_xlink_href xml_buffer, energy_floor_area{}.energy_floor_area_energy_type xml_char(19), energy_floor_area{}.energy_floor_area_energy_value xml_real64, energy_floor_area{}.energy_floor_area_energy_value_units xml_buffer,
      citygml_level_of_detail{} xml_buffer, energy_average_internal_gains_energy_heat_exchange_type_energy_convective_fraction xml_real64, energy_average_internal_gains_energy_heat_exchange_type_energy_convective_fraction_units xml_buffer, energy_average_internal_gains_energy_heat_exchange_type_energy_latent_fraction xml_real64, energy_average_internal_gains_energy_heat_exchange_type_energy_latent_fraction_units xml_buffer, energy_average_internal_gains_energy_heat_exchange_type_energy_radiant_fraction xml_real64, energy_average_internal_gains_energy_heat_exchange_type_energy_radiant_fraction_units xml_buffer, energy_average_internal_gains_energy_heat_exchange_type_energy_total_value xml_real64, energy_average_internal_gains_energy_heat_exchange_type_energy_total_value_units xml_buffer, energy_contains{}.xlink_href xml_buffer, energy_occupied_by{}.xlink_href xml_buffer, energy_equipped_with{}.xlink_href xml_buffer
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, citygml_level_of_detail{} xml_buffer, citygml_opening{}.xlink_href xml_buffer
    -> WallSurface (writer CITYGML_2)
WallSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, citygml_level_of_detail{} xml_buffer, citygml_opening{}.xlink_href xml_buffer
WeatherStation (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_station_name xml_buffer, energy_parameter{} xml_xml, energy_parameter{}.xlink_href xml_buffer
    -> WeatherStation (writer CITYGML_2)
WeatherStation (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_station_name xml_buffer, energy_parameter{} xml_xml, energy_parameter{}.xlink_href xml_buffer
Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> AttributeManager_8
AirCompressor (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_compressor_type xml_char(35), energy_pressure xml_real64, energy_pressure_units xml_buffer
    -> AttributeManager_16
Boiler (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_has_condensation xml_boolean
    -> AttributeManager
Building (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64,
      citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, energy_aggregated_building_construction{}.xlink_href xml_buffer, energy_building_type{} xml_buffer, energy_building_type{}.codeSpace xml_buffer, energy_construction_weight{} xml_char(9), energy_energy_performance_certification{}.energy_energy_performance_certification_energy_rating xml_buffer, energy_energy_performance_certification{}.energy_energy_performance_certification_energy_name xml_buffer, energy_energy_performance_certification{}.energy_energy_performance_certification_energy_certification_id xml_buffer, energy_floor_area{}.energy_floor_area_energy_type xml_char(19), energy_floor_area{}.energy_floor_area_energy_value xml_real64, energy_floor_area{}.energy_floor_area_energy_value_units xml_buffer, energy_height_above_ground{}.energy_height_above_ground_energy_height_reference xml_char(22), energy_height_above_ground{}.energy_height_above_ground_energy_value xml_real64, energy_height_above_ground{}.energy_height_above_ground_energy_value_units xml_buffer, energy_is_landmarked{} xml_boolean, energy_refurbishment_measure{}.energy_refurbishment_measure_energy_date_energy_date_of_event_energy_instant xml_buffer, energy_refurbishment_measure{}.energy_refurbishment_measure_energy_date_energy_date_of_event_energy_instant_frame xml_buffer, energy_refurbishment_measure{}.energy_refurbishment_measure_energy_date_energy_date_of_event_energy_instant_calendarEraName xml_buffer, energy_refurbishment_measure{}.energy_refurbishment_measure_energy_date_energy_date_of_event_energy_instant_indeterminatePosition xml_char(7), energy_refurbishment_measure{}.energy_refurbishment_measure_energy_date_energy_date_of_event_energy_period_xlink_href xml_buffer,
      energy_refurbishment_measure{}.energy_refurbishment_measure_energy_date_energy_date_of_event_energy_period_gml_time_period_frame xml_buffer, energy_refurbishment_measure{}.energy_refurbishment_measure_energy_date_energy_date_of_event_energy_period_gml_time_period_gml_id xml_buffer, energy_refurbishment_measure{}.energy_refurbishment_measure_energy_date_energy_date_of_event_energy_period_gml_time_period_gml_related_time{}.relativePosition xml_char(12), energy_refurbishment_measure{}.energy_refurbishment_measure_energy_date_energy_date_of_event_energy_period_gml_time_period_gml_related_time{}.xlink_href xml_buffer, energy_refurbishment_measure{}.energy_refurbishment_measure_energy_date_energy_date_of_event_energy_period_gml_time_period_gml_related_time{}.gml_time_edge_gml_id xml_buffer, energy_refurbishment_measure{}.energy_refurbishment_measure_energy_date_energy_date_of_event_energy_period_gml_time_period_gml_related_time{}.gml_time_edge_gml_related_time{} xml_xml, energy_refurbishment_measure{}.energy_refurbishment_measure_energy_date_energy_date_of_event_energy_period_gml_time_period_gml_related_time{}.gml_time_edge_gml_related_time{}.relativePosition xml_char(12), energy_refurbishment_measure{}.energy_refurbishment_measure_energy_date_energy_date_of_event_energy_period_gml_time_period_gml_related_time{}.gml_time_edge_gml_related_time{}.xlink_href xml_buffer, energy_refurbishment_measure{}.energy_refurbishment_measure_energy_date_energy_date_of_event_energy_period_gml_time_period_gml_related_time{}.gml_time_edge_gml_complex_xlink_href xml_buffer, energy_refurbishment_measure{}.energy_refurbishment_measure_energy_date_energy_date_of_event_energy_period_gml_time_period_gml_related_time{}.gml_time_edge_gml_start_xlink_href xml_buffer, energy_refurbishment_measure{}.energy_refurbishment_measure_energy_date_energy_date_of_event_energy_period_gml_time_period_gml_related_time{}.gml_time_edge_gml_start_gml_time_node_gml_id xml_buffer, energy_refurbishment_measure{}.energy_refurbishment_measure_energy_date_energy_date_of_event_energy_period_gml_time_period_gml_related_time{}.gml_time_edge_gml_start_gml_time_node_gml_related_time{} xml_xml, energy_refurbishment_measure{}.energy_refurbishment_measure_energy_date_energy_date_of_event_energy_period_gml_time_period_gml_related_time{}.gml_time_edge_gml_start_gml_time_node_gml_related_time{}.relativePosition xml_char(12), energy_refurbishment_measure{}.energy_refurbishment_measure_energy_date_energy_date_of_event_energy_period_gml_time_period_gml_related_time{}.gml_time_edge_gml_start_gml_time_node_gml_related_time{}.xlink_href xml_buffer, energy_refurbishment_measure{}.energy_refurbishment_measure_energy_date_energy_date_of_event_energy_period_gml_time_period_gml_related_time{}.gml_time_edge_gml_start_gml_time_node_gml_complex_xlink_href xml_buffer, energy_refurbishment_measure{}.energy_refurbishment_measure_energy_date_energy_date_of_event_energy_period_gml_time_period_gml_related_time{}.gml_time_edge_gml_start_gml_time_node_gml_previous_edge{}.xlink_href xml_buffer, energy_refurbishment_measure{}.energy_refurbishment_measure_energy_date_energy_date_of_event_energy_period_gml_time_period_gml_related_time{}.gml_time_edge_gml_start_gml_time_node_gml_previous_edge{}.gml_time_edge xml_xml, energy_refurbishment_measure{}.energy_refurbishment_measure_energy_date_energy_date_of_event_energy_period_gml_time_period_gml_related_time{}.gml_time_edge_gml_start_gml_time_node_gml_previous_edge{}.gml_time_edge_gml_id xml_buffer, energy_refurbishment_measure{}.energy_refurbishment_measure_energy_date_energy_date_of_event_energy_period_gml_time_period_gml_related_time{}.gml_time_edge_gml_start_gml_time_node_gml_next_edge{}.xlink_href xml_buffer, energy_refurbishment_measure{}.energy_refurbishment_measure_energy_date_energy_date_of_event_energy_period_gml_time_period_gml_related_time{}.gml_time_edge_gml_start_gml_time_node_gml_next_edge{}.gml_time_edge xml_xml, energy_refurbishment_measure{}.energy_refurbishment_measure_energy_date_energy_date_of_event_energy_period_gml_time_period_gml_related_time{}.gml_time_edge_gml_start_gml_time_node_gml_next_edge{}.gml_time_edge_gml_id xml_buffer, energy_refurbishment_measure{}.energy_refurbishment_measure_energy_date_energy_date_of_event_energy_period_gml_time_period_gml_related_time{}.gml_time_edge_gml_start_gml_time_node_gml_position_xlink_href xml_buffer, energy_refurbishment_measure{}.energy_refurbishment_measure_energy_date_energy_date_of_event_energy_period_gml_time_period_gml_related_time{}.gml_time_edge_gml_start_gml_time_node_gml_position_gml_time_instant_frame xml_buffer, energy_refurbishment_measure{}.energy_refurbishment_measure_energy_date_energy_date_of_event_energy_period_gml_time_period_gml_related_time{}.gml_time_edge_gml_start_gml_time_node_gml_position_gml_time_instant_gml_id xml_buffer, energy_refurbishment_measure{}.energy_refurbishment_measure_energy_date_energy_date_of_event_energy_period_gml_time_period_gml_related_time{}.gml_time_edge_gml_start_gml_time_node_gml_position_gml_time_instant_gml_related_time{} xml_xml, energy_refurbishment_measure{}.energy_refurbishment_measure_energy_date_energy_date_of_event_energy_period_gml_time_period_gml_related_time{}.gml_time_edge_gml_start_gml_time_node_gml_position_gml_time_instant_gml_related_time{}.relativePosition xml_char(12), energy_refurbishment_measure{}.energy_refurbishment_measure_energy_date_energy_date_of_event_energy_period_gml_time_period_gml_related_time{}.gml_time_edge_gml_start_gml_time_node_gml_position_gml_time_instant_gml_related_time{}.xlink_href xml_buffer, energy_refurbishment_measure{}.energy_refurbishment_measure_energy_date_energy_date_of_event_energy_period_gml_time_period_gml_related_time{}.gml_time_edge_gml_start_gml_time_node_gml_position_gml_time_instant_gml_time_position xml_buffer, energy_refurbishment_measure{}.energy_refurbishment_measure_energy_date_energy_date_of_event_energy_period_gml_time_period_gml_related_time{}.gml_time_edge_gml_start_gml_time_node_gml_position_gml_time_instant_gml_time_position_frame xml_buffer, energy_refurbishment_measure{}.energy_refurbishment_measure_energy_date_energy_date_of_event_energy_period_gml_time_period_gml_related_time{}.gml_time_edge_gml_start_gml_time_node_gml_position_gml_time_instant_gml_time_position_calendarEraName xml_buffer,
      energy_refurbishment_measure{}.energy_refurbishment_measure_energy_date_energy_date_of_event_energy_period_gml_time_period_gml_related_time{}.gml_time_edge_gml_start_gml_time_node_gml_position_gml_time_instant_gml_time_position_indeterminatePosition xml_char(7), energy_refurbishment_measure{}.energy_refurbishment_measure_energy_date_energy_date_of_event_energy_period_gml_time_period_gml_related_time{}.gml_time_edge_gml_end_xlink_href xml_buffer, energy_refurbishment_measure{}.energy_refurbishment_measure_energy_date_energy_date_of_event_energy_period_gml_time_period_gml_related_time{}.gml_time_edge_gml_end_gml_time_node_gml_id xml_buffer, energy_refurbishment_measure{}.energy_refurbishment_measure_energy_date_energy_date_of_event_energy_period_gml_time_period_gml_related_time{}.gml_time_edge_gml_end_gml_time_node_gml_related_time{} xml_xml, energy_refurbishment_measure{}.energy_refurbishment_measure_energy_date_energy_date_of_event_energy_period_gml_time_period_gml_related_time{}.gml_time_edge_gml_end_gml_time_node_gml_related_time{}.relativePosition xml_char(12), energy_refurbishment_measure{}.energy_refurbishment_measure_energy_date_energy_date_of_event_energy_period_gml_time_period_gml_related_time{}.gml_time_edge_gml_end_gml_time_node_gml_related_time{}.xlink_href xml_buffer, energy_refurbishment_measure{}.energy_refurbishment_measure_energy_date_energy_date_of_event_energy_period_gml_time_period_gml_related_time{}.gml_time_edge_gml_end_gml_time_node_gml_complex_xlink_href xml_buffer, energy_refurbishment_measure{}.energy_refurbishment_measure_energy_date_energy_date_of_event_energy_period_gml_time_period_gml_related_time{}.gml_time_edge_gml_end_gml_time_node_gml_previous_edge{}.xlink_href xml_buffer, energy_refurbishment_measure{}.energy_refurbishment_measure_energy_date_energy_date_of_event_energy_period_gml_time_period_gml_related_time{}.gml_time_edge_gml_end_gml_time_node_gml_previous_edge{}.gml_time_edge xml_xml, energy_refurbishment_measure{}.energy_refurbishment_measure_energy_date_energy_date_of_event_energy_period_gml_time_period_gml_related_time{}.gml_time_edge_gml_end_gml_time_node_gml_previous_edge{}.gml_time_edge_gml_id xml_buffer, energy_refurbishment_measure{}.energy_refurbishment_measure_energy_date_energy_date_of_event_energy_period_gml_time_period_gml_related_time{}.gml_time_edge_gml_end_gml_time_node_gml_next_edge{}.xlink_href xml_buffer, energy_refurbishment_measure{}.energy_refurbishment_measure_energy_date_energy_date_of_event_energy_period_gml_time_period_gml_related_time{}.gml_time_edge_gml_end_gml_time_node_gml_next_edge{}.gml_time_edge xml_xml, energy_refurbishment_measure{}.energy_refurbishment_measure_energy_date_energy_date_of_event_energy_period_gml_time_period_gml_related_time{}.gml_time_edge_gml_end_gml_time_node_gml_next_edge{}.gml_time_edge_gml_id xml_buffer, energy_refurbishment_measure{}.energy_refurbishment_measure_energy_date_energy_date_of_event_energy_period_gml_time_period_gml_related_time{}.gml_time_edge_gml_end_gml_time_node_gml_position_xlink_href xml_buffer, energy_refurbishment_measure{}.energy_refurbishment_measure_energy_date_energy_date_of_event_energy_period_gml_time_period_gml_related_time{}.gml_time_edge_gml_end_gml_time_node_gml_position_gml_time_instant_frame xml_buffer, energy_refurbishment_measure{}.energy_refurbishment_measure_energy_date_energy_date_of_event_energy_period_gml_time_period_gml_related_time{}.gml_time_edge_gml_end_gml_time_node_gml_position_gml_time_instant_gml_id xml_buffer, energy_refurbishment_measure{}.energy_refurbishment_measure_energy_date_energy_date_of_event_energy_period_gml_time_period_gml_related_time{}.gml_time_edge_gml_end_gml_time_node_gml_position_gml_time_instant_gml_related_time{} xml_xml, energy_refurbishment_measure{}.energy_refurbishment_measure_energy_date_energy_date_of_event_energy_period_gml_time_period_gml_related_time{}.gml_time_edge_gml_end_gml_time_node_gml_position_gml_time_instant_gml_related_time{}.relativePosition xml_char(12), energy_refurbishment_measure{}.energy_refurbishment_measure_energy_date_energy_date_of_event_energy_period_gml_time_period_gml_related_time{}.gml_time_edge_gml_end_gml_time_node_gml_position_gml_time_instant_gml_related_time{}.xlink_href xml_buffer, energy_refurbishment_measure{}.energy_refurbishment_measure_energy_date_energy_date_of_event_energy_period_gml_time_period_gml_related_time{}.gml_time_edge_gml_end_gml_time_node_gml_position_gml_time_instant_gml_time_position xml_buffer, energy_refurbishment_measure{}.energy_refurbishment_measure_energy_date_energy_date_of_event_energy_period_gml_time_period_gml_related_time{}.gml_time_edge_gml_end_gml_time_node_gml_position_gml_time_instant_gml_time_position_frame xml_buffer, energy_refurbishment_measure{}.energy_refurbishment_measure_energy_date_energy_date_of_event_energy_period_gml_time_period_gml_related_time{}.gml_time_edge_gml_end_gml_time_node_gml_position_gml_time_instant_gml_time_position_calendarEraName xml_buffer, energy_refurbishment_measure{}.energy_refurbishment_measure_energy_date_energy_date_of_event_energy_period_gml_time_period_gml_related_time{}.gml_time_edge_gml_end_gml_time_node_gml_position_gml_time_instant_gml_time_position_indeterminatePosition xml_char(7), energy_refurbishment_measure{}.energy_refurbishment_measure_energy_date_energy_date_of_event_energy_period_gml_time_period_gml_related_time{}.gml_time_edge_gml_extent_xlink_href xml_buffer, energy_refurbishment_measure{}.energy_refurbishment_measure_energy_date_energy_date_of_event_energy_period_gml_time_period_gml_related_time{}.gml_time_edge_gml_extent_gml_time_period xml_xml, energy_refurbishment_measure{}.energy_refurbishment_measure_energy_date_energy_date_of_event_energy_period_gml_time_period_gml_related_time{}.gml_time_edge_gml_extent_gml_time_period_frame xml_buffer, energy_refurbishment_measure{}.energy_refurbishment_measure_energy_date_energy_date_of_event_energy_period_gml_time_period_gml_related_time{}.gml_time_edge_gml_extent_gml_time_period_gml_id xml_buffer, energy_refurbishment_measure{}.energy_refurbishment_measure_energy_date_energy_date_of_event_energy_period_gml_time_period_gml_related_time{}.gml_time_instant_frame xml_buffer, energy_refurbishment_measure{}.energy_refurbishment_measure_energy_date_energy_date_of_event_energy_period_gml_time_period_gml_related_time{}.gml_time_instant_gml_id xml_buffer, energy_refurbishment_measure{}.energy_refurbishment_measure_energy_date_energy_date_of_event_energy_period_gml_time_period_gml_related_time{}.gml_time_instant_gml_related_time{} xml_xml,
      energy_refurbishment_measure{}.energy_refurbishment_measure_energy_date_energy_date_of_event_energy_period_gml_time_period_gml_related_time{}.gml_time_instant_gml_related_time{}.relativePosition xml_char(12), energy_refurbishment_measure{}.energy_refurbishment_measure_energy_date_energy_date_of_event_energy_period_gml_time_period_gml_related_time{}.gml_time_instant_gml_related_time{}.xlink_href xml_buffer, energy_refurbishment_measure{}.energy_refurbishment_measure_energy_date_energy_date_of_event_energy_period_gml_time_period_gml_related_time{}.gml_time_instant_gml_time_position xml_buffer, energy_refurbishment_measure{}.energy_refurbishment_measure_energy_date_energy_date_of_event_energy_period_gml_time_period_gml_related_time{}.gml_time_instant_gml_time_position_frame xml_buffer, energy_refurbishment_measure{}.energy_refurbishment_measure_energy_date_energy_date_of_event_energy_period_gml_time_period_gml_related_time{}.gml_time_instant_gml_time_position_calendarEraName xml_buffer, energy_refurbishment_measure{}.energy_refurbishment_measure_energy_date_energy_date_of_event_energy_period_gml_time_period_gml_related_time{}.gml_time_instant_gml_time_position_indeterminatePosition xml_char(7), energy_refurbishment_measure{}.energy_refurbishment_measure_energy_date_energy_date_of_event_energy_period_gml_time_period_gml_related_time{}.gml_time_node_gml_id xml_buffer, energy_refurbishment_measure{}.energy_refurbishment_measure_energy_date_energy_date_of_event_energy_period_gml_time_period_gml_related_time{}.gml_time_node_gml_related_time{} xml_xml, energy_refurbishment_measure{}.energy_refurbishment_measure_energy_date_energy_date_of_event_energy_period_gml_time_period_gml_related_time{}.gml_time_node_gml_related_time{}.relativePosition xml_char(12), energy_refurbishment_measure{}.energy_refurbishment_measure_energy_date_energy_date_of_event_energy_period_gml_time_period_gml_related_time{}.gml_time_node_gml_related_time{}.xlink_href xml_buffer, energy_refurbishment_measure{}.energy_refurbishment_measure_energy_date_energy_date_of_event_energy_period_gml_time_period_gml_related_time{}.gml_time_node_gml_complex_xlink_href xml_buffer, energy_refurbishment_measure{}.energy_refurbishment_measure_energy_date_energy_date_of_event_energy_period_gml_time_period_gml_related_time{}.gml_time_node_gml_previous_edge{}.xlink_href xml_buffer, energy_refurbishment_measure{}.energy_refurbishment_measure_energy_date_energy_date_of_event_energy_period_gml_time_period_gml_related_time{}.gml_time_node_gml_previous_edge{}.gml_time_edge_gml_id xml_buffer, energy_refurbishment_measure{}.energy_refurbishment_measure_energy_date_energy_date_of_event_energy_period_gml_time_period_gml_related_time{}.gml_time_node_gml_previous_edge{}.gml_time_edge_gml_related_time{} xml_xml, energy_refurbishment_measure{}.energy_refurbishment_measure_energy_date_energy_date_of_event_energy_period_gml_time_period_gml_related_time{}.gml_time_node_gml_previous_edge{}.gml_time_edge_gml_related_time{}.relativePosition xml_char(12), energy_refurbishment_measure{}.energy_refurbishment_measure_energy_date_energy_date_of_event_energy_period_gml_time_period_gml_related_time{}.gml_time_node_gml_previous_edge{}.gml_time_edge_gml_related_time{}.xlink_href xml_buffer, energy_refurbishment_measure{}.energy_refurbishment_measure_energy_date_energy_date_of_event_energy_period_gml_time_period_gml_related_time{}.gml_time_node_gml_previous_edge{}.gml_time_edge_gml_complex_xlink_href xml_buffer, energy_refurbishment_measure{}.energy_refurbishment_measure_energy_date_energy_date_of_event_energy_period_gml_time_period_gml_related_time{}.gml_time_node_gml_previous_edge{}.gml_time_edge_gml_start_xlink_href xml_buffer, energy_refurbishment_measure{}.energy_refurbishment_measure_energy_date_energy_date_of_event_energy_period_gml_time_period_gml_related_time{}.gml_time_node_gml_previous_edge{}.gml_time_edge_gml_start_gml_time_node xml_xml, energy_refurbishment_measure{}.energy_refurbishment_measure_energy_date_energy_date_of_event_energy_period_gml_time_period_gml_related_time{}.gml_time_node_gml_previous_edge{}.gml_time_edge_gml_start_gml_time_node_gml_id xml_buffer, energy_refurbishment_measure{}.energy_refurbishment_measure_energy_date_energy_date_of_event_energy_period_gml_time_period_gml_related_time{}.gml_time_node_gml_previous_edge{}.gml_time_edge_gml_end_xlink_href xml_buffer, energy_refurbishment_measure{}.energy_refurbishment_measure_energy_date_energy_date_of_event_energy_period_gml_time_period_gml_related_time{}.gml_time_node_gml_previous_edge{}.gml_time_edge_gml_end_gml_time_node xml_xml, energy_refurbishment_measure{}.energy_refurbishment_measure_energy_date_energy_date_of_event_energy_period_gml_time_period_gml_related_time{}.gml_time_node_gml_previous_edge{}.gml_time_edge_gml_end_gml_time_node_gml_id xml_buffer, energy_refurbishment_measure{}.energy_refurbishment_measure_energy_date_energy_date_of_event_energy_period_gml_time_period_gml_related_time{}.gml_time_node_gml_previous_edge{}.gml_time_edge_gml_extent_xlink_href xml_buffer, energy_refurbishment_measure{}.energy_refurbishment_measure_energy_date_energy_date_of_event_energy_period_gml_time_period_gml_related_time{}.gml_time_node_gml_previous_edge{}.gml_time_edge_gml_extent_gml_time_period xml_xml, energy_refurbishment_measure{}.energy_refurbishment_measure_energy_date_energy_date_of_event_energy_period_gml_time_period_gml_related_time{}.gml_time_node_gml_previous_edge{}.gml_time_edge_gml_extent_gml_time_period_frame xml_buffer, energy_refurbishment_measure{}.energy_refurbishment_measure_energy_date_energy_date_of_event_energy_period_gml_time_period_gml_related_time{}.gml_time_node_gml_previous_edge{}.gml_time_edge_gml_extent_gml_time_period_gml_id xml_buffer, energy_refurbishment_measure{}.energy_refurbishment_measure_energy_date_energy_date_of_event_energy_period_gml_time_period_gml_related_time{}.gml_time_node_gml_next_edge{}.xlink_href xml_buffer, energy_refurbishment_measure{}.energy_refurbishment_measure_energy_date_energy_date_of_event_energy_period_gml_time_period_gml_related_time{}.gml_time_node_gml_next_edge{}.gml_time_edge_gml_id xml_buffer, energy_refurbishment_measure{}.energy_refurbishment_measure_energy_date_energy_date_of_event_energy_period_gml_time_period_gml_related_time{}.gml_time_node_gml_next_edge{}.gml_time_edge_gml_related_time{} xml_xml,
      energy_refurbishment_measure{}.energy_refurbishment_measure_energy_date_energy_date_of_event_energy_period_gml_time_period_gml_related_time{}.gml_time_node_gml_next_edge{}.gml_time_edge_gml_related_time{}.relativePosition xml_char(12), energy_refurbishment_measure{}.energy_refurbishment_measure_energy_date_energy_date_of_event_energy_period_gml_time_period_gml_related_time{}.gml_time_node_gml_next_edge{}.gml_time_edge_gml_related_time{}.xlink_href xml_buffer, energy_refurbishment_measure{}.energy_refurbishment_measure_energy_date_energy_date_of_event_energy_period_gml_time_period_gml_related_time{}.gml_time_node_gml_next_edge{}.gml_time_edge_gml_complex_xlink_href xml_buffer, energy_refurbishment_measure{}.energy_refurbishment_measure_energy_date_energy_date_of_event_energy_period_gml_time_period_gml_related_time{}.gml_time_node_gml_next_edge{}.gml_time_edge_gml_start_xlink_href xml_buffer, energy_refurbishment_measure{}.energy_refurbishment_measure_energy_date_energy_date_of_event_energy_period_gml_time_period_gml_related_time{}.gml_time_node_gml_next_edge{}.gml_time_edge_gml_start_gml_time_node xml_xml, energy_refurbishment_measure{}.energy_refurbishment_measure_energy_date_energy_date_of_event_energy_period_gml_time_period_gml_related_time{}.gml_time_node_gml_next_edge{}.gml_time_edge_gml_start_gml_time_node_gml_id xml_buffer, energy_refurbishment_measure{}.energy_refurbishment_measure_energy_date_energy_date_of_event_energy_period_gml_time_period_gml_related_time{}.gml_time_node_gml_next_edge{}.gml_time_edge_gml_end_xlink_href xml_buffer, energy_refurbishment_measure{}.energy_refurbishment_measure_energy_date_energy_date_of_event_energy_period_gml_time_period_gml_related_time{}.gml_time_node_gml_next_edge{}.gml_time_edge_gml_end_gml_time_node xml_xml, energy_refurbishment_measure{}.energy_refurbishment_measure_energy_date_energy_date_of_event_energy_period_gml_time_period_gml_related_time{}.gml_time_node_gml_next_edge{}.gml_time_edge_gml_end_gml_time_node_gml_id xml_buffer, energy_refurbishment_measure{}.energy_refurbishment_measure_energy_date_energy_date_of_event_energy_period_gml_time_period_gml_related_time{}.gml_time_node_gml_next_edge{}.gml_time_edge_gml_extent_xlink_href xml_buffer, energy_refurbishment_measure{}.energy_refurbishment_measure_energy_date_energy_date_of_event_energy_period_gml_time_period_gml_related_time{}.gml_time_node_gml_next_edge{}.gml_time_edge_gml_extent_gml_time_period xml_xml, energy_refurbishment_measure{}.energy_refurbishment_measure_energy_date_energy_date_of_event_energy_period_gml_time_period_gml_related_time{}.gml_time_node_gml_next_edge{}.gml_time_edge_gml_extent_gml_time_period_frame xml_buffer, energy_refurbishment_measure{}.energy_refurbishment_measure_energy_date_energy_date_of_event_energy_period_gml_time_period_gml_related_time{}.gml_time_node_gml_next_edge{}.gml_time_edge_gml_extent_gml_time_period_gml_id xml_buffer, energy_refurbishment_measure{}.energy_refurbishment_measure_energy_date_energy_date_of_event_energy_period_gml_time_period_gml_related_time{}.gml_time_node_gml_position_xlink_href xml_buffer, energy_refurbishment_measure{}.energy_refurbishment_measure_energy_date_energy_date_of_event_energy_period_gml_time_period_gml_related_time{}.gml_time_node_gml_position_gml_time_instant_frame xml_buffer, energy_refurbishment_measure{}.energy_refurbishment_measure_energy_date_energy_date_of_event_energy_period_gml_time_period_gml_related_time{}.gml_time_node_gml_position_gml_time_instant_gml_id xml_buffer, energy_refurbishment_measure{}.energy_refurbishment_measure_energy_date_energy_date_of_event_energy_period_gml_time_period_gml_related_time{}.gml_time_node_gml_position_gml_time_instant_gml_related_time{} xml_xml, energy_refurbishment_measure{}.energy_refurbishment_measure_energy_date_energy_date_of_event_energy_period_gml_time_period_gml_related_time{}.gml_time_node_gml_position_gml_time_instant_gml_related_time{}.relativePosition xml_char(12), energy_refurbishment_measure{}.energy_refurbishment_measure_energy_date_energy_date_of_event_energy_period_gml_time_period_gml_related_time{}.gml_time_node_gml_position_gml_time_instant_gml_related_time{}.xlink_href xml_buffer, energy_refurbishment_measure{}.energy_refurbishment_measure_energy_date_energy_date_of_event_energy_period_gml_time_period_gml_related_time{}.gml_time_node_gml_position_gml_time_instant_gml_time_position xml_buffer, energy_refurbishment_measure{}.energy_refurbishment_measure_energy_date_energy_date_of_event_energy_period_gml_time_period_gml_related_time{}.gml_time_node_gml_position_gml_time_instant_gml_time_position_frame xml_buffer, energy_refurbishment_measure{}.energy_refurbishment_measure_energy_date_energy_date_of_event_energy_period_gml_time_period_gml_related_time{}.gml_time_node_gml_position_gml_time_instant_gml_time_position_calendarEraName xml_buffer, energy_refurbishment_measure{}.energy_refurbishment_measure_energy_date_energy_date_of_event_energy_period_gml_time_period_gml_related_time{}.gml_time_node_gml_position_gml_time_instant_gml_time_position_indeterminatePosition xml_char(7), energy_refurbishment_measure{}.energy_refurbishment_measure_energy_date_energy_date_of_event_energy_period_gml_time_period_gml_related_time{}.gml_time_period xml_xml, energy_refurbishment_measure{}.energy_refurbishment_measure_energy_date_energy_date_of_event_energy_period_gml_time_period_gml_related_time{}.gml_time_period_frame xml_buffer, energy_refurbishment_measure{}.energy_refurbishment_measure_energy_date_energy_date_of_event_energy_period_gml_time_period_gml_related_time{}.gml_time_period_gml_id xml_buffer, energy_refurbishment_measure{}.energy_refurbishment_measure_energy_date_energy_date_of_event_energy_period_gml_time_period_gml_begin_position xml_buffer, energy_refurbishment_measure{}.energy_refurbishment_measure_energy_date_energy_date_of_event_energy_period_gml_time_period_gml_begin_position_frame xml_buffer, energy_refurbishment_measure{}.energy_refurbishment_measure_energy_date_energy_date_of_event_energy_period_gml_time_period_gml_begin_position_calendarEraName xml_buffer, energy_refurbishment_measure{}.energy_refurbishment_measure_energy_date_energy_date_of_event_energy_period_gml_time_period_gml_begin_position_indeterminatePosition xml_char(7),
      energy_refurbishment_measure{}.energy_refurbishment_measure_energy_date_energy_date_of_event_energy_period_gml_time_period_gml_begin_xlink_href xml_buffer, energy_refurbishment_measure{}.energy_refurbishment_measure_energy_date_energy_date_of_event_energy_period_gml_time_period_gml_begin_gml_time_instant_frame xml_buffer, energy_refurbishment_measure{}.energy_refurbishment_measure_energy_date_energy_date_of_event_energy_period_gml_time_period_gml_begin_gml_time_instant_gml_id xml_buffer, energy_refurbishment_measure{}.energy_refurbishment_measure_energy_date_energy_date_of_event_energy_period_gml_time_period_gml_begin_gml_time_instant_gml_related_time{}.relativePosition xml_char(12), energy_refurbishment_measure{}.energy_refurbishment_measure_energy_date_energy_date_of_event_energy_period_gml_time_period_gml_begin_gml_time_instant_gml_related_time{}.xlink_href xml_buffer, energy_refurbishment_measure{}.energy_refurbishment_measure_energy_date_energy_date_of_event_energy_period_gml_time_period_gml_begin_gml_time_instant_gml_related_time{}.gml_time_edge_gml_id xml_buffer, energy_refurbishment_measure{}.energy_refurbishment_measure_energy_date_energy_date_of_event_energy_period_gml_time_period_gml_begin_gml_time_instant_gml_related_time{}.gml_time_edge_gml_related_time{} xml_xml, energy_refurbishment_measure{}.energy_refurbishment_measure_energy_date_energy_date_of_event_energy_period_gml_time_period_gml_begin_gml_time_instant_gml_related_time{}.gml_time_edge_gml_related_time{}.relativePosition xml_char(12), energy_refurbishment_measure{}.energy_refurbishment_measure_energy_date_energy_date_of_event_energy_period_gml_time_period_gml_begin_gml_time_instant_gml_related_time{}.gml_time_edge_gml_related_time{}.xlink_href xml_buffer, energy_refurbishment_measure{}.energy_refurbishment_measure_energy_date_energy_date_of_event_energy_period_gml_time_period_gml_begin_gml_time_instant_gml_related_time{}.gml_time_edge_gml_complex_xlink_href xml_buffer, energy_refurbishment_measure{}.energy_refurbishment_measure_energy_date_energy_date_of_event_energy_period_gml_time_period_gml_begin_gml_time_instant_gml_related_time{}.gml_time_edge_gml_start_xlink_href xml_buffer, energy_refurbishment_measure{}.energy_refurbishment_measure_energy_date_energy_date_of_event_energy_period_gml_time_period_gml_begin_gml_time_instant_gml_related_time{}.gml_time_edge_gml_start_gml_time_node_gml_id xml_buffer, energy_refurbishment_measure{}.energy_refurbishment_measure_energy_date_energy_date_of_event_energy_period_gml_time_period_gml_begin_gml_time_instant_gml_related_time{}.gml_time_edge_gml_start_gml_time_node_gml_related_time{} xml_xml, energy_refurbishment_measure{}.energy_refurbishment_measure_energy_date_energy_date_of_event_energy_period_gml_time_period_gml_begin_gml_time_instant_gml_related_time{}.gml_time_edge_gml_start_gml_time_node_gml_related_time{}.relativePosition xml_char(12), energy_refurbishment_measure{}.energy_refurbishment_measure_energy_date_energy_date_of_event_energy_period_gml_time_period_gml_begin_gml_time_instant_gml_related_time{}.gml_time_edge_gml_start_gml_time_node_gml_related_time{}.xlink_href xml_buffer, energy_refurbishment_measure{}.energy_refurbishment_measure_energy_date_energy_date_of_event_energy_period_gml_time_period_gml_begin_gml_time_instant_gml_related_time{}.gml_time_edge_gml_start_gml_time_node_gml_complex_xlink_href xml_buffer, energy_refurbishment_measure{}.energy_refurbishment_measure_energy_date_energy_date_of_event_energy_period_gml_time_period_gml_begin_gml_time_instant_gml_related_time{}.gml_time_edge_gml_start_gml_time_node_gml_previous_edge{}.xlink_href xml_buffer, energy_refurbishment_measure{}.energy_refurbishment_measure_energy_date_energy_date_of_event_energy_period_gml_time_period_gml_begin_gml_time_instant_gml_related_time{}.gml_time_edge_gml_start_gml_time_node_gml_previous_edge{}.gml_time_edge xml_xml, energy_refurbishment_measure{}.energy_refurbishment_measure_energy_date_energy_date_of_event_energy_period_gml_time_period_gml_begin_gml_time_instant_gml_related_time{}.gml_time_edge_gml_start_gml_time_node_gml_previous_edge{}.gml_time_edge_gml_id xml_buffer, energy_refurbishment_measure{}.energy_refurbishment_measure_energy_date_energy_date_of_event_energy_period_gml_time_period_gml_begin_gml_time_instant_gml_related_time{}.gml_time_edge_gml_start_gml_time_node_gml_next_edge{}.xlink_href xml_buffer, energy_refurbishment_measure{}.energy_refurbishment_measure_energy_date_energy_date_of_event_energy_period_gml_time_period_gml_begin_gml_time_instant_gml_related_time{}.gml_time_edge_gml_start_gml_time_node_gml_next_edge{}.gml_time_edge xml_xml, energy_refurbishment_measure{}.energy_refurbishment_measure_energy_date_energy_date_of_event_energy_period_gml_time_period_gml_begin_gml_time_instant_gml_related_time{}.gml_time_edge_gml_start_gml_time_node_gml_next_edge{}.gml_time_edge_gml_id xml_buffer, energy_refurbishment_measure{}.energy_refurbishment_measure_energy_date_energy_date_of_event_energy_period_gml_time_period_gml_begin_gml_time_instant_gml_related_time{}.gml_time_edge_gml_start_gml_time_node_gml_position_xlink_href xml_buffer, energy_refurbishment_measure{}.energy_refurbishment_measure_energy_date_energy_date_of_event_energy_period_gml_time_period_gml_begin_gml_time_instant_gml_related_time{}.gml_time_edge_gml_start_gml_time_node_gml_position_gml_time_instant xml_xml, energy_refurbishment_measure{}.energy_refurbishment_measure_energy_date_energy_date_of_event_energy_period_gml_time_period_gml_begin_gml_time_instant_gml_related_time{}.gml_time_edge_gml_start_gml_time_node_gml_position_gml_time_instant_frame xml_buffer, energy_refurbishment_measure{}.energy_refurbishment_measure_energy_date_energy_date_of_event_energy_period_gml_time_period_gml_begin_gml_time_instant_gml_related_time{}.gml_time_edge_gml_start_gml_time_node_gml_position_gml_time_instant_gml_id xml_buffer, energy_refurbishment_measure{}.energy_refurbishment_measure_energy_date_energy_date_of_event_energy_period_gml_time_period_gml_begin_gml_time_instant_gml_related_time{}.gml_time_edge_gml_end_xlink_href xml_buffer, energy_refurbishment_measure{}.energy_refurbishment_measure_energy_date_energy_date_of_event_energy_period_gml_time_period_gml_begin_gml_time_instant_gml_related_time{}.gml_time_edge_gml_end_gml_time_node_gml_id xml_buffer, energy_refurbishment_measure{}.energy_refurbishment_measure_energy_date_energy_date_of_event_energy_period_gml_time_period_gml_begin_gml_time_instant_gml_related_time{}.gml_time_edge_gml_end_gml_time_node_gml_related_time{} xml_xml, energy_refurbishment_measure{}.energy_refurbishment_measure_energy_date_energy_date_of_event_energy_period_gml_time_period_gml_begin_gml_time_instant_gml_related_time{}.gml_time_edge_gml_end_gml_time_node_gml_related_time{}.relativePosition xml_char(12),
      energy_refurbishment_measure{}.energy_refurbishment_measure_energy_date_energy_date_of_event_energy_period_gml_time_period_gml_begin_gml_time_instant_gml_related_time{}.gml_time_edge_gml_end_gml_time_node_gml_related_time{}.xlink_href xml_buffer, energy_refurbishment_measure{}.energy_refurbishment_measure_energy_date_energy_date_of_event_energy_period_gml_time_period_gml_begin_gml_time_instant_gml_related_time{}.gml_time_edge_gml_end_gml_time_node_gml_complex_xlink_href xml_buffer, energy_refurbishment_measure{}.energy_refurbishment_measure_energy_date_energy_date_of_event_energy_period_gml_time_period_gml_begin_gml_time_instant_gml_related_time{}.gml_time_edge_gml_end_gml_time_node_gml_previous_edge{}.xlink_href xml_buffer, energy_refurbishment_measure{}.energy_refurbishment_measure_energy_date_energy_date_of_event_energy_period_gml_time_period_gml_begin_gml_time_instant_gml_related_time{}.gml_time_edge_gml_end_gml_time_node_gml_previous_edge{}.gml_time_edge xml_xml, energy_refurbishment_measure{}.energy_refurbishment_measure_energy_date_energy_date_of_event_energy_period_gml_time_period_gml_begin_gml_time_instant_gml_related_time{}.gml_time_edge_gml_end_gml_time_node_gml_previous_edge{}.gml_time_edge_gml_id xml_buffer, energy_refurbishment_measure{}.energy_refurbishment_measure_energy_date_energy_date_of_event_energy_period_gml_time_period_gml_begin_gml_time_instant_gml_related_time{}.gml_time_edge_gml_end_gml_time_node_gml_next_edge{}.xlink_href xml_buffer, energy_refurbishment_measure{}.energy_refurbishment_measure_energy_date_energy_date_of_event_energy_period_gml_time_period_gml_begin_gml_time_instant_gml_related_time{}.gml_time_edge_gml_end_gml_time_node_gml_next_edge{}.gml_time_edge xml_xml, energy_refurbishment_measure{}.energy_refurbishment_measure_energy_date_energy_date_of_event_energy_period_gml_time_period_gml_begin_gml_time_instant_gml_related_time{}.gml_time_edge_gml_end_gml_time_node_gml_next_edge{}.gml_time_edge_gml_id xml_buffer, energy_refurbishment_measure{}.energy_refurbishment_measure_energy_date_energy_date_of_event_energy_period_gml_time_period_gml_begin_gml_time_instant_gml_related_time{}.gml_time_edge_gml_end_gml_time_node_gml_position_xlink_href xml_buffer, energy_refurbishment_measure{}.energy_refurbishment_measure_energy_date_energy_date_of_event_energy_period_gml_time_period_gml_begin_gml_time_instant_gml_related_time{}.gml_time_edge_gml_end_gml_time_node_gml_position_gml_time_instant xml_xml, energy_refurbishment_measure{}.energy_refurbishment_measure_energy_date_energy_date_of_event_energy_period_gml_time_period_gml_begin_gml_time_instant_gml_related_time{}.gml_time_edge_gml_end_gml_time_node_gml_position_gml_time_instant_frame xml_buffer, energy_refurbishment_measure{}.energy_refurbishment_measure_energy_date_energy_date_of_event_energy_period_gml_time_period_gml_begin_gml_time_instant_gml_related_time{}.gml_time_edge_gml_end_gml_time_node_gml_position_gml_time_instant_gml_id xml_buffer, energy_refurbishment_measure{}.energy_refurbishment_measure_energy_date_energy_date_of_event_energy_period_gml_time_period_gml_begin_gml_time_instant_gml_related_time{}.gml_time_edge_gml_extent_xlink_href xml_buffer, energy_refurbishment_measure{}.energy_refurbishment_measure_energy_date_energy_date_of_event_energy_period_gml_time_period_gml_begin_gml_time_instant_gml_related_time{}.gml_time_edge_gml_extent_gml_time_period xml_xml, energy_refurbishment_measure{}.energy_refurbishment_measure_energy_date_energy_date_of_event_energy_period_gml_time_period_gml_begin_gml_time_instant_gml_related_time{}.gml_time_edge_gml_extent_gml_time_period_frame xml_buffer, energy_refurbishment_measure{}.energy_refurbishment_measure_energy_date_energy_date_of_event_energy_period_gml_time_period_gml_begin_gml_time_instant_gml_related_time{}.gml_time_edge_gml_extent_gml_time_period_gml_id xml_buffer, energy_refurbishment_measure{}.energy_refurbishment_measure_energy_date_energy_date_of_event_energy_period_gml_time_period_gml_begin_gml_time_instant_gml_related_time{}.gml_time_instant xml_xml, energy_refurbishment_measure{}.energy_refurbishment_measure_energy_date_energy_date_of_event_energy_period_gml_time_period_gml_begin_gml_time_instant_gml_related_time{}.gml_time_instant_frame xml_buffer, energy_refurbishment_measure{}.energy_refurbishment_measure_energy_date_energy_date_of_event_energy_period_gml_time_period_gml_begin_gml_time_instant_gml_related_time{}.gml_time_instant_gml_id xml_buffer, energy_refurbishment_measure{}.energy_refurbishment_measure_energy_date_energy_date_of_event_energy_period_gml_time_period_gml_begin_gml_time_instant_gml_related_time{}.gml_time_node_gml_id xml_buffer, energy_refurbishment_measure{}.energy_refurbishment_measure_energy_date_energy_date_of_event_energy_period_gml_time_period_gml_begin_gml_time_instant_gml_related_time{}.gml_time_node_gml_related_time{} xml_xml, energy_refurbishment_measure{}.energy_refurbishment_measure_energy_date_energy_date_of_event_energy_period_gml_time_period_gml_begin_gml_time_instant_gml_related_time{}.gml_time_node_gml_related_time{}.relativePosition xml_char(12), energy_refurbishment_measure{}.energy_refurbishment_measure_energy_date_energy_date_of_event_energy_period_gml_time_period_gml_begin_gml_time_instant_gml_related_time{}.gml_time_node_gml_related_time{}.xlink_href xml_buffer, energy_refurbishment_measure{}.energy_refurbishment_measure_energy_date_energy_date_of_event_energy_period_gml_time_period_gml_begin_gml_time_instant_gml_related_time{}.gml_time_node_gml_complex_xlink_href xml_buffer, energy_refurbishment_measure{}.energy_refurbishment_measure_energy_date_energy_date_of_event_energy_period_gml_time_period_gml_begin_gml_time_instant_gml_related_time{}.gml_time_node_gml_previous_edge{}.xlink_href xml_buffer, energy_refurbishment_measure{}.energy_refurbishment_measure_energy_date_energy_date_of_event_energy_period_gml_time_period_gml_begin_gml_time_instant_gml_related_time{}.gml_time_node_gml_previous_edge{}.gml_time_edge_gml_id xml_buffer, energy_refurbishment_measure{}.energy_refurbishment_measure_energy_date_energy_date_of_event_energy_period_gml_time_period_gml_begin_gml_time_instant_gml_related_time{}.gml_time_node_gml_previous_edge{}.gml_time_edge_gml_related_time{} xml_xml, energy_refurbishment_measure{}.energy_refurbishment_measure_energy_date_energy_date_of_event_energy_period_gml_time_period_gml_begin_gml_time_instant_gml_related_time{}.gml_time_node_gml_previous_edge{}.gml_time_edge_gml_related_time{}.relativePosition xml_char(12), energy_refurbishment_measure{}.energy_refurbishment_measure_energy_date_energy_date_of_event_energy_period_gml_time_period_gml_begin_gml_time_instant_gml_related_time{}.gml_time_node_gml_previous_edge{}.gml_time_edge_gml_related_time{}.xlink_href xml_buffer, energy_refurbishment_measure{}.energy_refurbishment_measure_energy_date_energy_date_of_event_energy_period_gml_time_period_gml_begin_gml_time_instant_gml_related_time{}.gml_time_node_gml_previous_edge{}.gml_time_edge_gml_complex_xlink_href xml_buffer,
      energy_refurbishment_measure{}.energy_refurbishment_measure_energy_date_energy_date_of_event_energy_period_gml_time_period_gml_begin_gml_time_instant_gml_related_time{}.gml_time_node_gml_previous_edge{}.gml_time_edge_gml_start_xlink_href xml_buffer, energy_refurbishment_measure{}.energy_refurbishment_measure_energy_date_energy_date_of_event_energy_period_gml_time_period_gml_begin_gml_time_instant_gml_related_time{}.gml_time_node_gml_previous_edge{}.gml_time_edge_gml_start_gml_time_node xml_xml, energy_refurbishment_measure{}.energy_refurbishment_measure_energy_date_energy_date_of_event_energy_period_gml_time_period_gml_begin_gml_time_instant_gml_related_time{}.gml_time_node_gml_previous_edge{}.gml_time_edge_gml_start_gml_time_node_gml_id xml_buffer, energy_refurbishment_measure{}.energy_refurbishment_measure_energy_date_energy_date_of_event_energy_period_gml_time_period_gml_begin_gml_time_instant_gml_related_time{}.gml_time_node_gml_previous_edge{}.gml_time_edge_gml_end_xlink_href xml_buffer, energy_refurbishment_measure{}.energy_refurbishment_measure_energy_date_energy_date_of_event_energy_period_gml_time_period_gml_begin_gml_time_instant_gml_related_time{}.gml_time_node_gml_previous_edge{}.gml_time_edge_gml_end_gml_time_node xml_xml, energy_refurbishment_measure{}.energy_refurbishment_measure_energy_date_energy_date_of_event_energy_period_gml_time_period_gml_begin_gml_time_instant_gml_related_time{}.gml_time_node_gml_previous_edge{}.gml_time_edge_gml_end_gml_time_node_gml_id xml_buffer, energy_refurbishment_measure{}.energy_refurbishment_measure_energy_date_energy_date_of_event_energy_period_gml_time_period_gml_begin_gml_time_instant_gml_related_time{}.gml_time_node_gml_previous_edge{}.gml_time_edge_gml_extent_xlink_href xml_buffer, energy_refurbishment_measure{}.energy_refurbishment_measure_energy_date_energy_date_of_event_energy_period_gml_time_period_gml_begin_gml_time_instant_gml_related_time{}.gml_time_node_gml_previous_edge{}.gml_time_edge_gml_extent_gml_time_period xml_xml, energy_refurbishment_measure{}.energy_refurbishment_measure_energy_date_energy_date_of_event_energy_period_gml_time_period_gml_begin_gml_time_instant_gml_related_time{}.gml_time_node_gml_previous_edge{}.gml_time_edge_gml_extent_gml_time_period_frame xml_buffer, energy_refurbishment_measure{}.energy_refurbishment_measure_energy_date_energy_date_of_event_energy_period_gml_time_period_gml_begin_gml_time_instant_gml_related_time{}.gml_time_node_gml_previous_edge{}.gml_time_edge_gml_extent_gml_time_period_gml_id xml_buffer, energy_refurbishment_measure{}.energy_refurbishment_measure_energy_date_energy_date_of_event_energy_period_gml_time_period_gml_begin_gml_time_instant_gml_related_time{}.gml_time_node_gml_next_edge{}.xlink_href xml_buffer, energy_refurbishment_measure{}.energy_refurbishment_measure_energy_date_energy_date_of_event_energy_period_gml_time_period_gml_begin_gml_time_instant_gml_related_time{}.gml_time_node_gml_next_edge{}.gml_time_edge_gml_id xml_buffer, energy_refurbishment_measure{}.energy_refurbishment_measure_energy_date_energy_date_of_event_energy_period_gml_time_period_gml_begin_gml_time_instant_gml_related_time{}.gml_time_node_gml_next_edge{}.gml_time_edge_gml_related_time{} xml_xml, energy_refurbishment_measure{}.energy_refurbishment_measure_energy_date_energy_date_of_event_energy_period_gml_time_period_gml_begin_gml_time_instant_gml_related_time{}.gml_time_node_gml_next_edge{}.gml_time_edge_gml_related_time{}.relativePosition xml_char(12), energy_refurbishment_measure{}.energy_refurbishment_measure_energy_date_energy_date_of_event_energy_period_gml_time_period_gml_begin_gml_time_instant_gml_related_time{}.gml_time_node_gml_next_edge{}.gml_time_edge_gml_related_time{}.xlink_href xml_buffer, energy_refurbishment_measure{}.energy_refurbishment_measure_energy_date_energy_date_of_event_energy_period_gml_time_period_gml_begin_gml_time_instant_gml_related_time{}.gml_time_node_gml_next_edge{}.gml_time_edge_gml_complex_xlink_href xml_buffer, energy_refurbishment_measure{}.energy_refurbishment_measure_energy_date_energy_date_of_event_energy_period_gml_time_period_gml_begin_gml_time_instant_gml_related_time{}.gml_time_node_gml_next_edge{}.gml_time_edge_gml_start_xlink_href xml_buffer, energy_refurbishment_measure{}.energy_refurbishment_measure_energy_date_energy_date_of_event_energy_period_gml_time_period_gml_begin_gml_time_instant_gml_related_time{}.gml_time_node_gml_next_edge{}.gml_time_edge_gml_start_gml_time_node xml_xml, energy_refurbishment_measure{}.energy_refurbishment_measure_energy_date_energy_date_of_event_energy_period_gml_time_period_gml_begin_gml_time_instant_gml_related_time{}.gml_time_node_gml_next_edge{}.gml_time_edge_gml_start_gml_time_node_gml_id xml_buffer, energy_refurbishment_measure{}.energy_refurbishment_measure_energy_date_energy_date_of_event_energy_period_gml_time_period_gml_begin_gml_time_instant_gml_related_time{}.gml_time_node_gml_next_edge{}.gml_time_edge_gml_end_xlink_href xml_buffer, energy_refurbishment_measure{}.energy_refurbishment_measure_energy_date_energy_date_of_event_energy_period_gml_time_period_gml_begin_gml_time_instant_gml_related_time{}.gml_time_node_gml_next_edge{}.gml_time_edge_gml_end_gml_time_node xml_xml, energy_refurbishment_measure{}.energy_refurbishment_measure_energy_date_energy_date_of_event_energy_period_gml_time_period_gml_begin_gml_time_instant_gml_related_time{}.gml_time_node_gml_next_edge{}.gml_time_edge_gml_end_gml_time_node_gml_id xml_buffer, energy_refurbishment_measure{}.energy_refurbishment_measure_energy_date_energy_date_of_event_energy_period_gml_time_period_gml_begin_gml_time_instant_gml_related_time{}.gml_time_node_gml_next_edge{}.gml_time_edge_gml_extent_xlink_href xml_buffer, energy_refurbishment_measure{}.energy_refurbishment_measure_energy_date_energy_date_of_event_energy_period_gml_time_period_gml_begin_gml_time_instant_gml_related_time{}.gml_time_node_gml_next_edge{}.gml_time_edge_gml_extent_gml_time_period xml_xml, energy_refurbishment_measure{}.energy_refurbishment_measure_energy_date_energy_date_of_event_energy_period_gml_time_period_gml_begin_gml_time_instant_gml_related_time{}.gml_time_node_gml_next_edge{}.gml_time_edge_gml_extent_gml_time_period_frame xml_buffer, energy_refurbishment_measure{}.energy_refurbishment_measure_energy_date_energy_date_of_event_energy_period_gml_time_period_gml_begin_gml_time_instant_gml_related_time{}.gml_time_node_gml_next_edge{}.gml_time_edge_gml_extent_gml_time_period_gml_id xml_buffer, energy_refurbishment_measure{}.energy_refurbishment_measure_energy_date_energy_date_of_event_energy_period_gml_time_period_gml_begin_gml_time_instant_gml_related_time{}.gml_time_node_gml_position_xlink_href xml_buffer, energy_refurbishment_measure{}.energy_refurbishment_measure_energy_date_energy_date_of_event_energy_period_gml_time_period_gml_begin_gml_time_instant_gml_related_time{}.gml_time_node_gml_position_gml_time_instant xml_xml, energy_refurbishment_measure{}.energy_refurbishment_measure_energy_date_energy_date_of_event_energy_period_gml_time_period_gml_begin_gml_time_instant_gml_related_time{}.gml_time_node_gml_position_gml_time_instant_frame xml_buffer, energy_refurbishment_measure{}.energy_refurbishment_measure_energy_date_energy_date_of_event_energy_period_gml_time_period_gml_begin_gml_time_instant_gml_related_time{}.gml_time_node_gml_position_gml_time_instant_gml_id xml_buffer,
      energy_refurbishment_measure{}.energy_refurbishment_measure_energy_date_energy_date_of_event_energy_period_gml_time_period_gml_begin_gml_time_instant_gml_related_time{}.gml_time_period xml_xml, energy_refurbishment_measure{}.energy_refurbishment_measure_energy_date_energy_date_of_event_energy_period_gml_time_period_gml_begin_gml_time_instant_gml_related_time{}.gml_time_period_frame xml_buffer, energy_refurbishment_measure{}.energy_refurbishment_measure_energy_date_energy_date_of_event_energy_period_gml_time_period_gml_begin_gml_time_instant_gml_related_time{}.gml_time_period_gml_id xml_buffer, energy_refurbishment_measure{}.energy_refurbishment_measure_energy_date_energy_date_of_event_energy_period_gml_time_period_gml_begin_gml_time_instant_gml_time_position xml_buffer, energy_refurbishment_measure{}.energy_refurbishment_measure_energy_date_energy_date_of_event_energy_period_gml_time_period_gml_begin_gml_time_instant_gml_time_position_frame xml_buffer, energy_refurbishment_measure{}.energy_refurbishment_measure_energy_date_energy_date_of_event_energy_period_gml_time_period_gml_begin_gml_time_instant_gml_time_position_calendarEraName xml_buffer, energy_refurbishment_measure{}.energy_refurbishment_measure_energy_date_energy_date_of_event_energy_period_gml_time_period_gml_begin_gml_time_instant_gml_time_position_indeterminatePosition xml_char(7), energy_refurbishment_measure{}.energy_refurbishment_measure_energy_date_energy_date_of_event_energy_period_gml_time_period_gml_end_position xml_buffer, energy_refurbishment_measure{}.energy_refurbishment_measure_energy_date_energy_date_of_event_energy_period_gml_time_period_gml_end_position_frame xml_buffer, energy_refurbishment_measure{}.energy_refurbishment_measure_energy_date_energy_date_of_event_energy_period_gml_time_period_gml_end_position_calendarEraName xml_buffer, energy_refurbishment_measure{}.energy_refurbishment_measure_energy_date_energy_date_of_event_energy_period_gml_time_period_gml_end_position_indeterminatePosition xml_char(7), energy_refurbishment_measure{}.energy_refurbishment_measure_energy_date_energy_date_of_event_energy_period_gml_time_period_gml_end_xlink_href xml_buffer, energy_refurbishment_measure{}.energy_refurbishment_measure_energy_date_energy_date_of_event_energy_period_gml_time_period_gml_end_gml_time_instant_frame xml_buffer, energy_refurbishment_measure{}.energy_refurbishment_measure_energy_date_energy_date_of_event_energy_period_gml_time_period_gml_end_gml_time_instant_gml_id xml_buffer, energy_refurbishment_measure{}.energy_refurbishment_measure_energy_date_energy_date_of_event_energy_period_gml_time_period_gml_end_gml_time_instant_gml_related_time{}.relativePosition xml_char(12), energy_refurbishment_measure{}.energy_refurbishment_measure_energy_date_energy_date_of_event_energy_period_gml_time_period_gml_end_gml_time_instant_gml_related_time{}.xlink_href xml_buffer, energy_refurbishment_measure{}.energy_refurbishment_measure_energy_date_energy_date_of_event_energy_period_gml_time_period_gml_end_gml_time_instant_gml_related_time{}.gml_time_edge_gml_id xml_buffer, energy_refurbishment_measure{}.energy_refurbishment_measure_energy_date_energy_date_of_event_energy_period_gml_time_period_gml_end_gml_time_instant_gml_related_time{}.gml_time_edge_gml_related_time{} xml_xml, energy_refurbishment_measure{}.energy_refurbishment_measure_energy_date_energy_date_of_event_energy_period_gml_time_period_gml_end_gml_time_instant_gml_related_time{}.gml_time_edge_gml_related_time{}.relativePosition xml_char(12), energy_refurbishment_measure{}.energy_refurbishment_measure_energy_date_energy_date_of_event_energy_period_gml_time_period_gml_end_gml_time_instant_gml_related_time{}.gml_time_edge_gml_related_time{}.xlink_href xml_buffer, energy_refurbishment_measure{}.energy_refurbishment_measure_energy_date_energy_date_of_event_energy_period_gml_time_period_gml_end_gml_time_instant_gml_related_time{}.gml_time_edge_gml_complex_xlink_href xml_buffer, energy_refurbishment_measure{}.energy_refurbishment_measure_energy_date_energy_date_of_event_energy_period_gml_time_period_gml_end_gml_time_instant_gml_related_time{}.gml_time_edge_gml_start_xlink_href xml_buffer, energy_refurbishment_measure{}.energy_refurbishment_measure_energy_date_energy_date_of_event_energy_period_gml_time_period_gml_end_gml_time_instant_gml_related_time{}.gml_time_edge_gml_start_gml_time_node_gml_id xml_buffer, energy_refurbishment_measure{}.energy_refurbishment_measure_energy_date_energy_date_of_event_energy_period_gml_time_period_gml_end_gml_time_instant_gml_related_time{}.gml_time_edge_gml_start_gml_time_node_gml_related_time{} xml_xml, energy_refurbishment_measure{}.energy_refurbishment_measure_energy_date_energy_date_of_event_energy_period_gml_time_period_gml_end_gml_time_instant_gml_related_time{}.gml_time_edge_gml_start_gml_time_node_gml_related_time{}.relativePosition xml_char(12), energy_refurbishment_measure{}.energy_refurbishment_measure_energy_date_energy_date_of_event_energy_period_gml_time_period_gml_end_gml_time_instant_gml_related_time{}.gml_time_edge_gml_start_gml_time_node_gml_related_time{}.xlink_href xml_buffer, energy_refurbishment_measure{}.energy_refurbishment_measure_energy_date_energy_date_of_event_energy_period_gml_time_period_gml_end_gml_time_instant_gml_related_time{}.gml_time_edge_gml_start_gml_time_node_gml_complex_xlink_href xml_buffer, energy_refurbishment_measure{}.energy_refurbishment_measure_energy_date_energy_date_of_event_energy_period_gml_time_period_gml_end_gml_time_instant_gml_related_time{}.gml_time_edge_gml_start_gml_time_node_gml_previous_edge{}.xlink_href xml_buffer, energy_refurbishment_measure{}.energy_refurbishment_measure_energy_date_energy_date_of_event_energy_period_gml_time_period_gml_end_gml_time_instant_gml_related_time{}.gml_time_edge_gml_start_gml_time_node_gml_previous_edge{}.gml_time_edge xml_xml, energy_refurbishment_measure{}.energy_refurbishment_measure_energy_date_energy_date_of_event_energy_period_gml_time_period_gml_end_gml_time_instant_gml_related_time{}.gml_time_edge_gml_start_gml_time_node_gml_previous_edge{}.gml_time_edge_gml_id xml_buffer,
      energy_refurbishment_measure{}.energy_refurbishment_measure_energy_date_energy_date_of_event_energy_period_gml_time_period_gml_end_gml_time_instant_gml_related_time{}.gml_time_edge_gml_start_gml_time_node_gml_next_edge{}.xlink_href xml_buffer, energy_refurbishment_measure{}.energy_refurbishment_measure_energy_date_energy_date_of_event_energy_period_gml_time_period_gml_end_gml_time_instant_gml_related_time{}.gml_time_edge_gml_start_gml_time_node_gml_next_edge{}.gml_time_edge xml_xml, energy_refurbishment_measure{}.energy_refurbishment_measure_energy_date_energy_date_of_event_energy_period_gml_time_period_gml_end_gml_time_instant_gml_related_time{}.gml_time_edge_gml_start_gml_time_node_gml_next_edge{}.gml_time_edge_gml_id xml_buffer, energy_refurbishment_measure{}.energy_refurbishment_measure_energy_date_energy_date_of_event_energy_period_gml_time_period_gml_end_gml_time_instant_gml_related_time{}.gml_time_edge_gml_start_gml_time_node_gml_position_xlink_href xml_buffer, energy_refurbishment_measure{}.energy_refurbishment_measure_energy_date_energy_date_of_event_energy_period_gml_time_period_gml_end_gml_time_instant_gml_related_time{}.gml_time_edge_gml_start_gml_time_node_gml_position_gml_time_instant xml_xml, energy_refurbishment_measure{}.energy_refurbishment_measure_energy_date_energy_date_of_event_energy_period_gml_time_period_gml_end_gml_time_instant_gml_related_time{}.gml_time_edge_gml_start_gml_time_node_gml_position_gml_time_instant_frame xml_buffer, energy_refurbishment_measure{}.energy_refurbishment_measure_energy_date_energy_date_of_event_energy_period_gml_time_period_gml_end_gml_time_instant_gml_related_time{}.gml_time_edge_gml_start_gml_time_node_gml_position_gml_time_instant_gml_id xml_buffer, energy_refurbishment_measure{}.energy_refurbishment_measure_energy_date_energy_date_of_event_energy_period_gml_time_period_gml_end_gml_time_instant_gml_related_time{}.gml_time_edge_gml_end_xlink_href xml_buffer, energy_refurbishment_measure{}.energy_refurbishment_measure_energy_date_energy_date_of_event_energy_period_gml_time_period_gml_end_gml_time_instant_gml_related_time{}.gml_time_edge_gml_end_gml_time_node_gml_id xml_buffer, energy_refurbishment_measure{}.energy_refurbishment_measure_energy_date_energy_date_of_event_energy_period_gml_time_period_gml_end_gml_time_instant_gml_related_time{}.gml_time_edge_gml_end_gml_time_node_gml_related_time{} xml_xml, energy_refurbishment_measure{}.energy_refurbishment_measure_energy_date_energy_date_of_event_energy_period_gml_time_period_gml_end_gml_time_instant_gml_related_time{}.gml_time_edge_gml_end_gml_time_node_gml_related_time{}.relativePosition xml_char(12), energy_refurbishment_measure{}.energy_refurbishment_measure_energy_date_energy_date_of_event_energy_period_gml_time_period_gml_end_gml_time_instant_gml_related_time{}.gml_time_edge_gml_end_gml_time_node_gml_related_time{}.xlink_href xml_buffer, energy_refurbishment_measure{}.energy_refurbishment_measure_energy_date_energy_date_of_event_energy_period_gml_time_period_gml_end_gml_time_instant_gml_related_time{}.gml_time_edge_gml_end_gml_time_node_gml_complex_xlink_href xml_buffer, energy_refurbishment_measure{}.energy_refurbishment_measure_energy_date_energy_date_of_event_energy_period_gml_time_period_gml_end_gml_time_instant_gml_related_time{}.gml_time_edge_gml_end_gml_time_node_gml_previous_edge{}.xlink_href xml_buffer, energy_refurbishment_measure{}.energy_refurbishment_measure_energy_date_energy_date_of_event_energy_period_gml_time_period_gml_end_gml_time_instant_gml_related_time{}.gml_time_edge_gml_end_gml_time_node_gml_previous_edge{}.gml_time_edge xml_xml, energy_refurbishment_measure{}.energy_refurbishment_measure_energy_date_energy_date_of_event_energy_period_gml_time_period_gml_end_gml_time_instant_gml_related_time{}.gml_time_edge_gml_end_gml_time_node_gml_previous_edge{}.gml_time_edge_gml_id xml_buffer, energy_refurbishment_measure{}.energy_refurbishment_measure_energy_date_energy_date_of_event_energy_period_gml_time_period_gml_end_gml_time_instant_gml_related_time{}.gml_time_edge_gml_end_gml_time_node_gml_next_edge{}.xlink_href xml_buffer, energy_refurbishment_measure{}.energy_refurbishment_measure_energy_date_energy_date_of_event_energy_period_gml_time_period_gml_end_gml_time_instant_gml_related_time{}.gml_time_edge_gml_end_gml_time_node_gml_next_edge{}.gml_time_edge xml_xml, energy_refurbishment_measure{}.energy_refurbishment_measure_energy_date_energy_date_of_event_energy_period_gml_time_period_gml_end_gml_time_instant_gml_related_time{}.gml_time_edge_gml_end_gml_time_node_gml_next_edge{}.gml_time_edge_gml_id xml_buffer, energy_refurbishment_measure{}.energy_refurbishment_measure_energy_date_energy_date_of_event_energy_period_gml_time_period_gml_end_gml_time_instant_gml_related_time{}.gml_time_edge_gml_end_gml_time_node_gml_position_xlink_href xml_buffer, energy_refurbishment_measure{}.energy_refurbishment_measure_energy_date_energy_date_of_event_energy_period_gml_time_period_gml_end_gml_time_instant_gml_related_time{}.gml_time_edge_gml_end_gml_time_node_gml_position_gml_time_instant xml_xml, energy_refurbishment_measure{}.energy_refurbishment_measure_energy_date_energy_date_of_event_energy_period_gml_time_period_gml_end_gml_time_instant_gml_related_time{}.gml_time_edge_gml_end_gml_time_node_gml_position_gml_time_instant_frame xml_buffer, energy_refurbishment_measure{}.energy_refurbishment_measure_energy_date_energy_date_of_event_energy_period_gml_time_period_gml_end_gml_time_instant_gml_related_time{}.gml_time_edge_gml_end_gml_time_node_gml_position_gml_time_instant_gml_id xml_buffer, energy_refurbishment_measure{}.energy_refurbishment_measure_energy_date_energy_date_of_event_energy_period_gml_time_period_gml_end_gml_time_instant_gml_related_time{}.gml_time_edge_gml_extent_xlink_href xml_buffer, energy_refurbishment_measure{}.energy_refurbishment_measure_energy_date_energy_date_of_event_energy_period_gml_time_period_gml_end_gml_time_instant_gml_related_time{}.gml_time_edge_gml_extent_gml_time_period xml_xml, energy_refurbishment_measure{}.energy_refurbishment_measure_energy_date_energy_date_of_event_energy_period_gml_time_period_gml_end_gml_time_instant_gml_related_time{}.gml_time_edge_gml_extent_gml_time_period_frame xml_buffer, energy_refurbishment_measure{}.energy_refurbishment_measure_energy_date_energy_date_of_event_energy_period_gml_time_period_gml_end_gml_time_instant_gml_related_time{}.gml_time_edge_gml_extent_gml_time_period_gml_id xml_buffer, energy_refurbishment_measure{}.energy_refurbishment_measure_energy_date_energy_date_of_event_energy_period_gml_time_period_gml_end_gml_time_instant_gml_related_time{}.gml_time_instant xml_xml, energy_refurbishment_measure{}.energy_refurbishment_measure_energy_date_energy_date_of_event_energy_period_gml_time_period_gml_end_gml_time_instant_gml_related_time{}.gml_time_instant_frame xml_buffer, energy_refurbishment_measure{}.energy_refurbishment_measure_energy_date_energy_date_of_event_energy_period_gml_time_period_gml_end_gml_time_instant_gml_related_time{}.gml_time_instant_gml_id xml_buffer,
      energy_refurbishment_measure{}.energy_refurbishment_measure_energy_date_energy_date_of_event_energy_period_gml_time_period_gml_end_gml_time_instant_gml_related_time{}.gml_time_node_gml_id xml_buffer, energy_refurbishment_measure{}.energy_refurbishment_measure_energy_date_energy_date_of_event_energy_period_gml_time_period_gml_end_gml_time_instant_gml_related_time{}.gml_time_node_gml_related_time{} xml_xml, energy_refurbishment_measure{}.energy_refurbishment_measure_energy_date_energy_date_of_event_energy_period_gml_time_period_gml_end_gml_time_instant_gml_related_time{}.gml_time_node_gml_related_time{}.relativePosition xml_char(12), energy_refurbishment_measure{}.energy_refurbishment_measure_energy_date_energy_date_of_event_energy_period_gml_time_period_gml_end_gml_time_instant_gml_related_time{}.gml_time_node_gml_related_time{}.xlink_href xml_buffer, energy_refurbishment_measure{}.energy_refurbishment_measure_energy_date_energy_date_of_event_energy_period_gml_time_period_gml_end_gml_time_instant_gml_related_time{}.gml_time_node_gml_complex_xlink_href xml_buffer, energy_refurbishment_measure{}.energy_refurbishment_measure_energy_date_energy_date_of_event_energy_period_gml_time_period_gml_end_gml_time_instant_gml_related_time{}.gml_time_node_gml_previous_edge{}.xlink_href xml_buffer, energy_refurbishment_measure{}.energy_refurbishment_measure_energy_date_energy_date_of_event_energy_period_gml_time_period_gml_end_gml_time_instant_gml_related_time{}.gml_time_node_gml_previous_edge{}.gml_time_edge_gml_id xml_buffer, energy_refurbishment_measure{}.energy_refurbishment_measure_energy_date_energy_date_of_event_energy_period_gml_time_period_gml_end_gml_time_instant_gml_related_time{}.gml_time_node_gml_previous_edge{}.gml_time_edge_gml_related_time{} xml_xml, energy_refurbishment_measure{}.energy_refurbishment_measure_energy_date_energy_date_of_event_energy_period_gml_time_period_gml_end_gml_time_instant_gml_related_time{}.gml_time_node_gml_previous_edge{}.gml_time_edge_gml_related_time{}.relativePosition xml_char(12), energy_refurbishment_measure{}.energy_refurbishment_measure_energy_date_energy_date_of_event_energy_period_gml_time_period_gml_end_gml_time_instant_gml_related_time{}.gml_time_node_gml_previous_edge{}.gml_time_edge_gml_related_time{}.xlink_href xml_buffer, energy_refurbishment_measure{}.energy_refurbishment_measure_energy_date_energy_date_of_event_energy_period_gml_time_period_gml_end_gml_time_instant_gml_related_time{}.gml_time_node_gml_previous_edge{}.gml_time_edge_gml_complex_xlink_href xml_buffer, energy_refurbishment_measure{}.energy_refurbishment_measure_energy_date_energy_date_of_event_energy_period_gml_time_period_gml_end_gml_time_instant_gml_related_time{}.gml_time_node_gml_previous_edge{}.gml_time_edge_gml_start_xlink_href xml_buffer, energy_refurbishment_measure{}.energy_refurbishment_measure_energy_date_energy_date_of_event_energy_period_gml_time_period_gml_end_gml_time_instant_gml_related_time{}.gml_time_node_gml_previous_edge{}.gml_time_edge_gml_start_gml_time_node xml_xml, energy_refurbishment_measure{}.energy_refurbishment_measure_energy_date_energy_date_of_event_energy_period_gml_time_period_gml_end_gml_time_instant_gml_related_time{}.gml_time_node_gml_previous_edge{}.gml_time_edge_gml_start_gml_time_node_gml_id xml_buffer, energy_refurbishment_measure{}.energy_refurbishment_measure_energy_date_energy_date_of_event_energy_period_gml_time_period_gml_end_gml_time_instant_gml_related_time{}.gml_time_node_gml_previous_edge{}.gml_time_edge_gml_end_xlink_href xml_buffer, energy_refurbishment_measure{}.energy_refurbishment_measure_energy_date_energy_date_of_event_energy_period_gml_time_period_gml_end_gml_time_instant_gml_related_time{}.gml_time_node_gml_previous_edge{}.gml_time_edge_gml_end_gml_time_node xml_xml, energy_refurbishment_measure{}.energy_refurbishment_measure_energy_date_energy_date_of_event_energy_period_gml_time_period_gml_end_gml_time_instant_gml_related_time{}.gml_time_node_gml_previous_edge{}.gml_time_edge_gml_end_gml_time_node_gml_id xml_buffer, energy_refurbishment_measure{}.energy_refurbishment_measure_energy_date_energy_date_of_event_energy_period_gml_time_period_gml_end_gml_time_instant_gml_related_time{}.gml_time_node_gml_previous_edge{}.gml_time_edge_gml_extent_xlink_href xml_buffer, energy_refurbishment_measure{}.energy_refurbishment_measure_energy_date_energy_date_of_event_energy_period_gml_time_period_gml_end_gml_time_instant_gml_related_time{}.gml_time_node_gml_previous_edge{}.gml_time_edge_gml_extent_gml_time_period xml_xml, energy_refurbishment_measure{}.energy_refurbishment_measure_energy_date_energy_date_of_event_energy_period_gml_time_period_gml_end_gml_time_instant_gml_related_time{}.gml_time_node_gml_previous_edge{}.gml_time_edge_gml_extent_gml_time_period_frame xml_buffer, energy_refurbishment_measure{}.energy_refurbishment_measure_energy_date_energy_date_of_event_energy_period_gml_time_period_gml_end_gml_time_instant_gml_related_time{}.gml_time_node_gml_previous_edge{}.gml_time_edge_gml_extent_gml_time_period_gml_id xml_buffer, energy_refurbishment_measure{}.energy_refurbishment_measure_energy_date_energy_date_of_event_energy_period_gml_time_period_gml_end_gml_time_instant_gml_related_time{}.gml_time_node_gml_next_edge{}.xlink_href xml_buffer, energy_refurbishment_measure{}.energy_refurbishment_measure_energy_date_energy_date_of_event_energy_period_gml_time_period_gml_end_gml_time_instant_gml_related_time{}.gml_time_node_gml_next_edge{}.gml_time_edge_gml_id xml_buffer, gml_description xml_buffer, gml_name xml_buffer, energy_refurbishment_measure{}.energy_refurbishment_measure_energy_date_energy_date_of_event_energy_period_gml_time_period_gml_end_gml_time_instant_gml_related_time{}.gml_time_node_gml_next_edge{}.gml_time_edge_gml_related_time{} xml_xml, energy_refurbishment_measure{}.energy_refurbishment_measure_energy_date_energy_date_of_event_energy_period_gml_time_period_gml_end_gml_time_instant_gml_related_time{}.gml_time_node_gml_next_edge{}.gml_time_edge_gml_related_time{}.relativePosition xml_char(12), energy_refurbishment_measure{}.energy_refurbishment_measure_energy_date_energy_date_of_event_energy_period_gml_time_period_gml_end_gml_time_instant_gml_related_time{}.gml_time_node_gml_next_edge{}.gml_time_edge_gml_related_time{}.xlink_href xml_buffer, energy_refurbishment_measure{}.energy_refurbishment_measure_energy_date_energy_date_of_event_energy_period_gml_time_period_gml_end_gml_time_instant_gml_related_time{}.gml_time_node_gml_next_edge{}.gml_time_edge_gml_complex_xlink_href xml_buffer, energy_refurbishment_measure{}.energy_refurbishment_measure_energy_date_energy_date_of_event_energy_period_gml_time_period_gml_end_gml_time_instant_gml_related_time{}.gml_time_node_gml_next_edge{}.gml_time_edge_gml_start_xlink_href xml_buffer,
      energy_refurbishment_measure{}.energy_refurbishment_measure_energy_date_energy_date_of_event_energy_period_gml_time_period_gml_end_gml_time_instant_gml_related_time{}.gml_time_node_gml_next_edge{}.gml_time_edge_gml_start_gml_time_node xml_xml, energy_refurbishment_measure{}.energy_refurbishment_measure_energy_date_energy_date_of_event_energy_period_gml_time_period_gml_end_gml_time_instant_gml_related_time{}.gml_time_node_gml_next_edge{}.gml_time_edge_gml_start_gml_time_node_gml_id xml_buffer, energy_refurbishment_measure{}.energy_refurbishment_measure_energy_date_energy_date_of_event_energy_period_gml_time_period_gml_end_gml_time_instant_gml_related_time{}.gml_time_node_gml_next_edge{}.gml_time_edge_gml_end_xlink_href xml_buffer, energy_refurbishment_measure{}.energy_refurbishment_measure_energy_date_energy_date_of_event_energy_period_gml_time_period_gml_end_gml_time_instant_gml_related_time{}.gml_time_node_gml_next_edge{}.gml_time_edge_gml_end_gml_time_node xml_xml, energy_refurbishment_measure{}.energy_refurbishment_measure_energy_date_energy_date_of_event_energy_period_gml_time_period_gml_end_gml_time_instant_gml_related_time{}.gml_time_node_gml_next_edge{}.gml_time_edge_gml_end_gml_time_node_gml_id xml_buffer, energy_refurbishment_measure{}.energy_refurbishment_measure_energy_date_energy_date_of_event_energy_period_gml_time_period_gml_end_gml_time_instant_gml_related_time{}.gml_time_node_gml_next_edge{}.gml_time_edge_gml_extent_xlink_href xml_buffer, energy_refurbishment_measure{}.energy_refurbishment_measure_energy_date_energy_date_of_event_energy_period_gml_time_period_gml_end_gml_time_instant_gml_related_time{}.gml_time_node_gml_next_edge{}.gml_time_edge_gml_extent_gml_time_period xml_xml, energy_refurbishment_measure{}.energy_refurbishment_measure_energy_date_energy_date_of_event_energy_period_gml_time_period_gml_end_gml_time_instant_gml_related_time{}.gml_time_node_gml_next_edge{}.gml_time_edge_gml_extent_gml_time_period_frame xml_buffer, energy_refurbishment_measure{}.energy_refurbishment_measure_energy_date_energy_date_of_event_energy_period_gml_time_period_gml_end_gml_time_instant_gml_related_time{}.gml_time_node_gml_next_edge{}.gml_time_edge_gml_extent_gml_time_period_gml_id xml_buffer, energy_refurbishment_measure{}.energy_refurbishment_measure_energy_date_energy_date_of_event_energy_period_gml_time_period_gml_end_gml_time_instant_gml_related_time{}.gml_time_node_gml_position_xlink_href xml_buffer, energy_refurbishment_measure{}.energy_refurbishment_measure_energy_date_energy_date_of_event_energy_period_gml_time_period_gml_end_gml_time_instant_gml_related_time{}.gml_time_node_gml_position_gml_time_instant xml_xml, energy_refurbishment_measure{}.energy_refurbishment_measure_energy_date_energy_date_of_event_energy_period_gml_time_period_gml_end_gml_time_instant_gml_related_time{}.gml_time_node_gml_position_gml_time_instant_frame xml_buffer, energy_refurbishment_measure{}.energy_refurbishment_measure_energy_date_energy_date_of_event_energy_period_gml_time_period_gml_end_gml_time_instant_gml_related_time{}.gml_time_node_gml_position_gml_time_instant_gml_id xml_buffer, energy_refurbishment_measure{}.energy_refurbishment_measure_energy_date_energy_date_of_event_energy_period_gml_time_period_gml_end_gml_time_instant_gml_related_time{}.gml_time_period xml_xml, energy_refurbishment_measure{}.energy_refurbishment_measure_energy_date_energy_date_of_event_energy_period_gml_time_period_gml_end_gml_time_instant_gml_related_time{}.gml_time_period_frame xml_buffer, energy_refurbishment_measure{}.energy_refurbishment_measure_energy_date_energy_date_of_event_energy_period_gml_time_period_gml_end_gml_time_instant_gml_related_time{}.gml_time_period_gml_id xml_buffer, energy_refurbishment_measure{}.energy_refurbishment_measure_energy_date_energy_date_of_event_energy_period_gml_time_period_gml_end_gml_time_instant_gml_time_position xml_buffer, energy_refurbishment_measure{}.energy_refurbishment_measure_energy_date_energy_date_of_event_energy_period_gml_time_period_gml_end_gml_time_instant_gml_time_position_frame xml_buffer, energy_refurbishment_measure{}.energy_refurbishment_measure_energy_date_energy_date_of_event_energy_period_gml_time_period_gml_end_gml_time_instant_gml_time_position_calendarEraName xml_buffer, energy_refurbishment_measure{}.energy_refurbishment_measure_energy_date_energy_date_of_event_energy_period_gml_time_period_gml_end_gml_time_instant_gml_time_position_indeterminatePosition xml_char(7), energy_refurbishment_measure{}.energy_refurbishment_measure_energy_date_energy_date_of_event_energy_period_gml_time_period_gml_duration xml_buffer, energy_refurbishment_measure{}.energy_refurbishment_measure_energy_date_energy_date_of_event_energy_period_gml_time_period_gml_time_interval xml_real64, energy_refurbishment_measure{}.energy_refurbishment_measure_energy_date_energy_date_of_event_energy_period_gml_time_period_gml_time_interval_unit xml_buffer, energy_refurbishment_measure{}.energy_refurbishment_measure_energy_date_energy_date_of_event_energy_period_gml_time_period_gml_time_interval_radix xml_uint64, energy_refurbishment_measure{}.energy_refurbishment_measure_energy_date_energy_date_of_event_energy_period_gml_time_period_gml_time_interval_factor xml_int64, energy_refurbishment_measure{}.energy_refurbishment_measure_energy_level xml_buffer, energy_refurbishment_measure{}.energy_refurbishment_measure_energy_level_codeSpace xml_buffer, energy_refurbishment_measure{}.energy_refurbishment_measure_energy_description xml_buffer, energy_thermal_zone{}.xlink_href xml_buffer, energy_usage_zone{}.xlink_href xml_buffer,
      energy_volume{}.energy_volume_type_energy_type xml_char(21), energy_volume{}.energy_volume_type_energy_value xml_real64, energy_volume{}.energy_volume_type_energy_value_units xml_buffer
    -> Building (writer CITYGML_2)
Building (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64,
      citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, energy_aggregated_building_construction{}.xlink_href xml_buffer, energy_building_type{} xml_buffer, energy_building_type{}.codeSpace xml_buffer, energy_construction_weight{} xml_char(9), energy_energy_performance_certification{}.energy_energy_performance_certification_energy_rating xml_buffer, energy_energy_performance_certification{}.energy_energy_performance_certification_energy_name xml_buffer, energy_energy_performance_certification{}.energy_energy_performance_certification_energy_certification_id xml_buffer, energy_floor_area{}.energy_floor_area_energy_type xml_char(19), energy_floor_area{}.energy_floor_area_energy_value xml_real64, energy_floor_area{}.energy_floor_area_energy_value_units xml_buffer, energy_height_above_ground{}.energy_height_above_ground_energy_height_reference xml_char(22), energy_height_above_ground{}.energy_height_above_ground_energy_value xml_real64, energy_height_above_ground{}.energy_height_above_ground_energy_value_units xml_buffer, energy_is_landmarked{} xml_boolean, energy_refurbishment_measure{}.energy_refurbishment_measure_energy_date_energy_date_of_event_energy_instant xml_buffer, energy_refurbishment_measure{}.energy_refurbishment_measure_energy_date_energy_date_of_event_energy_instant_frame xml_buffer, energy_refurbishment_measure{}.energy_refurbishment_measure_energy_date_energy_date_of_event_energy_instant_calendarEraName xml_buffer, energy_refurbishment_measure{}.energy_refurbishment_measure_energy_date_energy_date_of_event_energy_instant_indeterminatePosition xml_char(7), energy_refurbishment_measure{}.energy_refurbishment_measure_energy_date_energy_date_of_event_energy_period_xlink_href xml_buffer,
      energy_refurbishment_measure{}.energy_refurbishment_measure_energy_date_energy_date_of_event_energy_period_gml_time_period_frame xml_buffer, energy_refurbishment_measure{}.energy_refurbishment_measure_energy_date_energy_date_of_event_energy_period_gml_time_period_gml_id xml_buffer, energy_refurbishment_measure{}.energy_refurbishment_measure_energy_date_energy_date_of_event_energy_period_gml_time_period_gml_related_time{}.relativePosition xml_char(12), energy_refurbishment_measure{}.energy_refurbishment_measure_energy_date_energy_date_of_event_energy_period_gml_time_period_gml_related_time{}.xlink_href xml_buffer, energy_refurbishment_measure{}.energy_refurbishment_measure_energy_date_energy_date_of_event_energy_period_gml_time_period_gml_related_time{}.gml_time_edge_gml_id xml_buffer, energy_refurbishment_measure{}.energy_refurbishment_measure_energy_date_energy_date_of_event_energy_period_gml_time_period_gml_related_time{}.gml_time_edge_gml_related_time{} xml_xml, energy_refurbishment_measure{}.energy_refurbishment_measure_energy_date_energy_date_of_event_energy_period_gml_time_period_gml_related_time{}.gml_time_edge_gml_related_time{}.relativePosition xml_char(12), energy_refurbishment_measure{}.energy_refurbishment_measure_energy_date_energy_date_of_event_energy_period_gml_time_period_gml_related_time{}.gml_time_edge_gml_related_time{}.xlink_href xml_buffer, energy_refurbishment_measure{}.energy_refurbishment_measure_energy_date_energy_date_of_event_energy_period_gml_time_period_gml_related_time{}.gml_time_edge_gml_complex_xlink_href xml_buffer, energy_refurbishment_measure{}.energy_refurbishment_measure_energy_date_energy_date_of_event_energy_period_gml_time_period_gml_related_time{}.gml_time_edge_gml_start_xlink_href xml_buffer, energy_refurbishment_measure{}.energy_refurbishment_measure_energy_date_energy_date_of_event_energy_period_gml_time_period_gml_related_time{}.gml_time_edge_gml_start_gml_time_node_gml_id xml_buffer, energy_refurbishment_measure{}.energy_refurbishment_measure_energy_date_energy_date_of_event_energy_period_gml_time_period_gml_related_time{}.gml_time_edge_gml_start_gml_time_node_gml_related_time{} xml_xml, energy_refurbishment_measure{}.energy_refurbishment_measure_energy_date_energy_date_of_event_energy_period_gml_time_period_gml_related_time{}.gml_time_edge_gml_start_gml_time_node_gml_related_time{}.relativePosition xml_char(12), energy_refurbishment_measure{}.energy_refurbishment_measure_energy_date_energy_date_of_event_energy_period_gml_time_period_gml_related_time{}.gml_time_edge_gml_start_gml_time_node_gml_related_time{}.xlink_href xml_buffer, energy_refurbishment_measure{}.energy_refurbishment_measure_energy_date_energy_date_of_event_energy_period_gml_time_period_gml_related_time{}.gml_time_edge_gml_start_gml_time_node_gml_complex_xlink_href xml_buffer, energy_refurbishment_measure{}.energy_refurbishment_measure_energy_date_energy_date_of_event_energy_period_gml_time_period_gml_related_time{}.gml_time_edge_gml_start_gml_time_node_gml_previous_edge{}.xlink_href xml_buffer, energy_refurbishment_measure{}.energy_refurbishment_measure_energy_date_energy_date_of_event_energy_period_gml_time_period_gml_related_time{}.gml_time_edge_gml_start_gml_time_node_gml_previous_edge{}.gml_time_edge xml_xml, energy_refurbishment_measure{}.energy_refurbishment_measure_energy_date_energy_date_of_event_energy_period_gml_time_period_gml_related_time{}.gml_time_edge_gml_start_gml_time_node_gml_previous_edge{}.gml_time_edge_gml_id xml_buffer, energy_refurbishment_measure{}.energy_refurbishment_measure_energy_date_energy_date_of_event_energy_period_gml_time_period_gml_related_time{}.gml_time_edge_gml_start_gml_time_node_gml_next_edge{}.xlink_href xml_buffer, energy_refurbishment_measure{}.energy_refurbishment_measure_energy_date_energy_date_of_event_energy_period_gml_time_period_gml_related_time{}.gml_time_edge_gml_start_gml_time_node_gml_next_edge{}.gml_time_edge xml_xml, energy_refurbishment_measure{}.energy_refurbishment_measure_energy_date_energy_date_of_event_energy_period_gml_time_period_gml_related_time{}.gml_time_edge_gml_start_gml_time_node_gml_next_edge{}.gml_time_edge_gml_id xml_buffer, energy_refurbishment_measure{}.energy_refurbishment_measure_energy_date_energy_date_of_event_energy_period_gml_time_period_gml_related_time{}.gml_time_edge_gml_start_gml_time_node_gml_position_xlink_href xml_buffer, energy_refurbishment_measure{}.energy_refurbishment_measure_energy_date_energy_date_of_event_energy_period_gml_time_period_gml_related_time{}.gml_time_edge_gml_start_gml_time_node_gml_position_gml_time_instant_frame xml_buffer, energy_refurbishment_measure{}.energy_refurbishment_measure_energy_date_energy_date_of_event_energy_period_gml_time_period_gml_related_time{}.gml_time_edge_gml_start_gml_time_node_gml_position_gml_time_instant_gml_id xml_buffer, energy_refurbishment_measure{}.energy_refurbishment_measure_energy_date_energy_date_of_event_energy_period_gml_time_period_gml_related_time{}.gml_time_edge_gml_start_gml_time_node_gml_position_gml_time_instant_gml_related_time{} xml_xml, energy_refurbishment_measure{}.energy_refurbishment_measure_energy_date_energy_date_of_event_energy_period_gml_time_period_gml_related_time{}.gml_time_edge_gml_start_gml_time_node_gml_position_gml_time_instant_gml_related_time{}.relativePosition xml_char(12), energy_refurbishment_measure{}.energy_refurbishment_measure_energy_date_energy_date_of_event_energy_period_gml_time_period_gml_related_time{}.gml_time_edge_gml_start_gml_time_node_gml_position_gml_time_instant_gml_related_time{}.xlink_href xml_buffer, energy_refurbishment_measure{}.energy_refurbishment_measure_energy_date_energy_date_of_event_energy_period_gml_time_period_gml_related_time{}.gml_time_edge_gml_start_gml_time_node_gml_position_gml_time_instant_gml_time_position xml_buffer, energy_refurbishment_measure{}.energy_refurbishment_measure_energy_date_energy_date_of_event_energy_period_gml_time_period_gml_related_time{}.gml_time_edge_gml_start_gml_time_node_gml_position_gml_time_instant_gml_time_position_frame xml_buffer, energy_refurbishment_measure{}.energy_refurbishment_measure_energy_date_energy_date_of_event_energy_period_gml_time_period_gml_related_time{}.gml_time_edge_gml_start_gml_time_node_gml_position_gml_time_instant_gml_time_position_calendarEraName xml_buffer,
      energy_refurbishment_measure{}.energy_refurbishment_measure_energy_date_energy_date_of_event_energy_period_gml_time_period_gml_related_time{}.gml_time_edge_gml_start_gml_time_node_gml_position_gml_time_instant_gml_time_position_indeterminatePosition xml_char(7), energy_refurbishment_measure{}.energy_refurbishment_measure_energy_date_energy_date_of_event_energy_period_gml_time_period_gml_related_time{}.gml_time_edge_gml_end_xlink_href xml_buffer, energy_refurbishment_measure{}.energy_refurbishment_measure_energy_date_energy_date_of_event_energy_period_gml_time_period_gml_related_time{}.gml_time_edge_gml_end_gml_time_node_gml_id xml_buffer, energy_refurbishment_measure{}.energy_refurbishment_measure_energy_date_energy_date_of_event_energy_period_gml_time_period_gml_related_time{}.gml_time_edge_gml_end_gml_time_node_gml_related_time{} xml_xml, energy_refurbishment_measure{}.energy_refurbishment_measure_energy_date_energy_date_of_event_energy_period_gml_time_period_gml_related_time{}.gml_time_edge_gml_end_gml_time_node_gml_related_time{}.relativePosition xml_char(12), energy_refurbishment_measure{}.energy_refurbishment_measure_energy_date_energy_date_of_event_energy_period_gml_time_period_gml_related_time{}.gml_time_edge_gml_end_gml_time_node_gml_related_time{}.xlink_href xml_buffer, energy_refurbishment_measure{}.energy_refurbishment_measure_energy_date_energy_date_of_event_energy_period_gml_time_period_gml_related_time{}.gml_time_edge_gml_end_gml_time_node_gml_complex_xlink_href xml_buffer, energy_refurbishment_measure{}.energy_refurbishment_measure_energy_date_energy_date_of_event_energy_period_gml_time_period_gml_related_time{}.gml_time_edge_gml_end_gml_time_node_gml_previous_edge{}.xlink_href xml_buffer, energy_refurbishment_measure{}.energy_refurbishment_measure_energy_date_energy_date_of_event_energy_period_gml_time_period_gml_related_time{}.gml_time_edge_gml_end_gml_time_node_gml_previous_edge{}.gml_time_edge xml_xml, energy_refurbishment_measure{}.energy_refurbishment_measure_energy_date_energy_date_of_event_energy_period_gml_time_period_gml_related_time{}.gml_time_edge_gml_end_gml_time_node_gml_previous_edge{}.gml_time_edge_gml_id xml_buffer, energy_refurbishment_measure{}.energy_refurbishment_measure_energy_date_energy_date_of_event_energy_period_gml_time_period_gml_related_time{}.gml_time_edge_gml_end_gml_time_node_gml_next_edge{}.xlink_href xml_buffer, energy_refurbishment_measure{}.energy_refurbishment_measure_energy_date_energy_date_of_event_energy_period_gml_time_period_gml_related_time{}.gml_time_edge_gml_end_gml_time_node_gml_next_edge{}.gml_time_edge xml_xml, energy_refurbishment_measure{}.energy_refurbishment_measure_energy_date_energy_date_of_event_energy_period_gml_time_period_gml_related_time{}.gml_time_edge_gml_end_gml_time_node_gml_next_edge{}.gml_time_edge_gml_id xml_buffer, energy_refurbishment_measure{}.energy_refurbishment_measure_energy_date_energy_date_of_event_energy_period_gml_time_period_gml_related_time{}.gml_time_edge_gml_end_gml_time_node_gml_position_xlink_href xml_buffer, energy_refurbishment_measure{}.energy_refurbishment_measure_energy_date_energy_date_of_event_energy_period_gml_time_period_gml_related_time{}.gml_time_edge_gml_end_gml_time_node_gml_position_gml_time_instant_frame xml_buffer, energy_refurbishment_measure{}.energy_refurbishment_measure_energy_date_energy_date_of_event_energy_period_gml_time_period_gml_related_time{}.gml_time_edge_gml_end_gml_time_node_gml_position_gml_time_instant_gml_id xml_buffer, energy_refurbishment_measure{}.energy_refurbishment_measure_energy_date_energy_date_of_event_energy_period_gml_time_period_gml_related_time{}.gml_time_edge_gml_end_gml_time_node_gml_position_gml_time_instant_gml_related_time{} xml_xml, energy_refurbishment_measure{}.energy_refurbishment_measure_energy_date_energy_date_of_event_energy_period_gml_time_period_gml_related_time{}.gml_time_edge_gml_end_gml_time_node_gml_position_gml_time_instant_gml_related_time{}.relativePosition xml_char(12), energy_refurbishment_measure{}.energy_refurbishment_measure_energy_date_energy_date_of_event_energy_period_gml_time_period_gml_related_time{}.gml_time_edge_gml_end_gml_time_node_gml_position_gml_time_instant_gml_related_time{}.xlink_href xml_buffer, energy_refurbishment_measure{}.energy_refurbishment_measure_energy_date_energy_date_of_event_energy_period_gml_time_period_gml_related_time{}.gml_time_edge_gml_end_gml_time_node_gml_position_gml_time_instant_gml_time_position xml_buffer, energy_refurbishment_measure{}.energy_refurbishment_measure_energy_date_energy_date_of_event_energy_period_gml_time_period_gml_related_time{}.gml_time_edge_gml_end_gml_time_node_gml_position_gml_time_instant_gml_time_position_frame xml_buffer, energy_refurbishment_measure{}.energy_refurbishment_measure_energy_date_energy_date_of_event_energy_period_gml_time_period_gml_related_time{}.gml_time_edge_gml_end_gml_time_node_gml_position_gml_time_instant_gml_time_position_calendarEraName xml_buffer, energy_refurbishment_measure{}.energy_refurbishment_measure_energy_date_energy_date_of_event_energy_period_gml_time_period_gml_related_time{}.gml_time_edge_gml_end_gml_time_node_gml_position_gml_time_instant_gml_time_position_indeterminatePosition xml_char(7), energy_refurbishment_measure{}.energy_refurbishment_measure_energy_date_energy_date_of_event_energy_period_gml_time_period_gml_related_time{}.gml_time_edge_gml_extent_xlink_href xml_buffer, energy_refurbishment_measure{}.energy_refurbishment_measure_energy_date_energy_date_of_event_energy_period_gml_time_period_gml_related_time{}.gml_time_edge_gml_extent_gml_time_period xml_xml, energy_refurbishment_measure{}.energy_refurbishment_measure_energy_date_energy_date_of_event_energy_period_gml_time_period_gml_related_time{}.gml_time_edge_gml_extent_gml_time_period_frame xml_buffer, energy_refurbishment_measure{}.energy_refurbishment_measure_energy_date_energy_date_of_event_energy_period_gml_time_period_gml_related_time{}.gml_time_edge_gml_extent_gml_time_period_gml_id xml_buffer, energy_refurbishment_measure{}.energy_refurbishment_measure_energy_date_energy_date_of_event_energy_period_gml_time_period_gml_related_time{}.gml_time_instant_frame xml_buffer, energy_refurbishment_measure{}.energy_refurbishment_measure_energy_date_energy_date_of_event_energy_period_gml_time_period_gml_related_time{}.gml_time_instant_gml_id xml_buffer, energy_refurbishment_measure{}.energy_refurbishment_measure_energy_date_energy_date_of_event_energy_period_gml_time_period_gml_related_time{}.gml_time_instant_gml_related_time{} xml_xml,
      energy_refurbishment_measure{}.energy_refurbishment_measure_energy_date_energy_date_of_event_energy_period_gml_time_period_gml_related_time{}.gml_time_instant_gml_related_time{}.relativePosition xml_char(12), energy_refurbishment_measure{}.energy_refurbishment_measure_energy_date_energy_date_of_event_energy_period_gml_time_period_gml_related_time{}.gml_time_instant_gml_related_time{}.xlink_href xml_buffer, energy_refurbishment_measure{}.energy_refurbishment_measure_energy_date_energy_date_of_event_energy_period_gml_time_period_gml_related_time{}.gml_time_instant_gml_time_position xml_buffer, energy_refurbishment_measure{}.energy_refurbishment_measure_energy_date_energy_date_of_event_energy_period_gml_time_period_gml_related_time{}.gml_time_instant_gml_time_position_frame xml_buffer, energy_refurbishment_measure{}.energy_refurbishment_measure_energy_date_energy_date_of_event_energy_period_gml_time_period_gml_related_time{}.gml_time_instant_gml_time_position_calendarEraName xml_buffer, energy_refurbishment_measure{}.energy_refurbishment_measure_energy_date_energy_date_of_event_energy_period_gml_time_period_gml_related_time{}.gml_time_instant_gml_time_position_indeterminatePosition xml_char(7), energy_refurbishment_measure{}.energy_refurbishment_measure_energy_date_energy_date_of_event_energy_period_gml_time_period_gml_related_time{}.gml_time_node_gml_id xml_buffer, energy_refurbishment_measure{}.energy_refurbishment_measure_energy_date_energy_date_of_event_energy_period_gml_time_period_gml_related_time{}.gml_time_node_gml_related_time{} xml_xml, energy_refurbishment_measure{}.energy_refurbishment_measure_energy_date_energy_date_of_event_energy_period_gml_time_period_gml_related_time{}.gml_time_node_gml_related_time{}.relativePosition xml_char(12), energy_refurbishment_measure{}.energy_refurbishment_measure_energy_date_energy_date_of_event_energy_period_gml_time_period_gml_related_time{}.gml_time_node_gml_related_time{}.xlink_href xml_buffer, energy_refurbishment_measure{}.energy_refurbishment_measure_energy_date_energy_date_of_event_energy_period_gml_time_period_gml_related_time{}.gml_time_node_gml_complex_xlink_href xml_buffer, energy_refurbishment_measure{}.energy_refurbishment_measure_energy_date_energy_date_of_event_energy_period_gml_time_period_gml_related_time{}.gml_time_node_gml_previous_edge{}.xlink_href xml_buffer, energy_refurbishment_measure{}.energy_refurbishment_measure_energy_date_energy_date_of_event_energy_period_gml_time_period_gml_related_time{}.gml_time_node_gml_previous_edge{}.gml_time_edge_gml_id xml_buffer, energy_refurbishment_measure{}.energy_refurbishment_measure_energy_date_energy_date_of_event_energy_period_gml_time_period_gml_related_time{}.gml_time_node_gml_previous_edge{}.gml_time_edge_gml_related_time{} xml_xml, energy_refurbishment_measure{}.energy_refurbishment_measure_energy_date_energy_date_of_event_energy_period_gml_time_period_gml_related_time{}.gml_time_node_gml_previous_edge{}.gml_time_edge_gml_related_time{}.relativePosition xml_char(12), energy_refurbishment_measure{}.energy_refurbishment_measure_energy_date_energy_date_of_event_energy_period_gml_time_period_gml_related_time{}.gml_time_node_gml_previous_edge{}.gml_time_edge_gml_related_time{}.xlink_href xml_buffer, energy_refurbishment_measure{}.energy_refurbishment_measure_energy_date_energy_date_of_event_energy_period_gml_time_period_gml_related_time{}.gml_time_node_gml_previous_edge{}.gml_time_edge_gml_complex_xlink_href xml_buffer, energy_refurbishment_measure{}.energy_refurbishment_measure_energy_date_energy_date_of_event_energy_period_gml_time_period_gml_related_time{}.gml_time_node_gml_previous_edge{}.gml_time_edge_gml_start_xlink_href xml_buffer, energy_refurbishment_measure{}.energy_refurbishment_measure_energy_date_energy_date_of_event_energy_period_gml_time_period_gml_related_time{}.gml_time_node_gml_previous_edge{}.gml_time_edge_gml_start_gml_time_node xml_xml, energy_refurbishment_measure{}.energy_refurbishment_measure_energy_date_energy_date_of_event_energy_period_gml_time_period_gml_related_time{}.gml_time_node_gml_previous_edge{}.gml_time_edge_gml_start_gml_time_node_gml_id xml_buffer, energy_refurbishment_measure{}.energy_refurbishment_measure_energy_date_energy_date_of_event_energy_period_gml_time_period_gml_related_time{}.gml_time_node_gml_previous_edge{}.gml_time_edge_gml_end_xlink_href xml_buffer, energy_refurbishment_measure{}.energy_refurbishment_measure_energy_date_energy_date_of_event_energy_period_gml_time_period_gml_related_time{}.gml_time_node_gml_previous_edge{}.gml_time_edge_gml_end_gml_time_node xml_xml, energy_refurbishment_measure{}.energy_refurbishment_measure_energy_date_energy_date_of_event_energy_period_gml_time_period_gml_related_time{}.gml_time_node_gml_previous_edge{}.gml_time_edge_gml_end_gml_time_node_gml_id xml_buffer, energy_refurbishment_measure{}.energy_refurbishment_measure_energy_date_energy_date_of_event_energy_period_gml_time_period_gml_related_time{}.gml_time_node_gml_previous_edge{}.gml_time_edge_gml_extent_xlink_href xml_buffer, energy_refurbishment_measure{}.energy_refurbishment_measure_energy_date_energy_date_of_event_energy_period_gml_time_period_gml_related_time{}.gml_time_node_gml_previous_edge{}.gml_time_edge_gml_extent_gml_time_period xml_xml, energy_refurbishment_measure{}.energy_refurbishment_measure_energy_date_energy_date_of_event_energy_period_gml_time_period_gml_related_time{}.gml_time_node_gml_previous_edge{}.gml_time_edge_gml_extent_gml_time_period_frame xml_buffer, energy_refurbishment_measure{}.energy_refurbishment_measure_energy_date_energy_date_of_event_energy_period_gml_time_period_gml_related_time{}.gml_time_node_gml_previous_edge{}.gml_time_edge_gml_extent_gml_time_period_gml_id xml_buffer, energy_refurbishment_measure{}.energy_refurbishment_measure_energy_date_energy_date_of_event_energy_period_gml_time_period_gml_related_time{}.gml_time_node_gml_next_edge{}.xlink_href xml_buffer, energy_refurbishment_measure{}.energy_refurbishment_measure_energy_date_energy_date_of_event_energy_period_gml_time_period_gml_related_time{}.gml_time_node_gml_next_edge{}.gml_time_edge_gml_id xml_buffer, energy_refurbishment_measure{}.energy_refurbishment_measure_energy_date_energy_date_of_event_energy_period_gml_time_period_gml_related_time{}.gml_time_node_gml_next_edge{}.gml_time_edge_gml_related_time{} xml_xml,
      energy_refurbishment_measure{}.energy_refurbishment_measure_energy_date_energy_date_of_event_energy_period_gml_time_period_gml_related_time{}.gml_time_node_gml_next_edge{}.gml_time_edge_gml_related_time{}.relativePosition xml_char(12), energy_refurbishment_measure{}.energy_refurbishment_measure_energy_date_energy_date_of_event_energy_period_gml_time_period_gml_related_time{}.gml_time_node_gml_next_edge{}.gml_time_edge_gml_related_time{}.xlink_href xml_buffer, energy_refurbishment_measure{}.energy_refurbishment_measure_energy_date_energy_date_of_event_energy_period_gml_time_period_gml_related_time{}.gml_time_node_gml_next_edge{}.gml_time_edge_gml_complex_xlink_href xml_buffer, energy_refurbishment_measure{}.energy_refurbishment_measure_energy_date_energy_date_of_event_energy_period_gml_time_period_gml_related_time{}.gml_time_node_gml_next_edge{}.gml_time_edge_gml_start_xlink_href xml_buffer, energy_refurbishment_measure{}.energy_refurbishment_measure_energy_date_energy_date_of_event_energy_period_gml_time_period_gml_related_time{}.gml_time_node_gml_next_edge{}.gml_time_edge_gml_start_gml_time_node xml_xml, energy_refurbishment_measure{}.energy_refurbishment_measure_energy_date_energy_date_of_event_energy_period_gml_time_period_gml_related_time{}.gml_time_node_gml_next_edge{}.gml_time_edge_gml_start_gml_time_node_gml_id xml_buffer, energy_refurbishment_measure{}.energy_refurbishment_measure_energy_date_energy_date_of_event_energy_period_gml_time_period_gml_related_time{}.gml_time_node_gml_next_edge{}.gml_time_edge_gml_end_xlink_href xml_buffer, energy_refurbishment_measure{}.energy_refurbishment_measure_energy_date_energy_date_of_event_energy_period_gml_time_period_gml_related_time{}.gml_time_node_gml_next_edge{}.gml_time_edge_gml_end_gml_time_node xml_xml, energy_refurbishment_measure{}.energy_refurbishment_measure_energy_date_energy_date_of_event_energy_period_gml_time_period_gml_related_time{}.gml_time_node_gml_next_edge{}.gml_time_edge_gml_end_gml_time_node_gml_id xml_buffer, energy_refurbishment_measure{}.energy_refurbishment_measure_energy_date_energy_date_of_event_energy_period_gml_time_period_gml_related_time{}.gml_time_node_gml_next_edge{}.gml_time_edge_gml_extent_xlink_href xml_buffer, energy_refurbishment_measure{}.energy_refurbishment_measure_energy_date_energy_date_of_event_energy_period_gml_time_period_gml_related_time{}.gml_time_node_gml_next_edge{}.gml_time_edge_gml_extent_gml_time_period xml_xml, energy_refurbishment_measure{}.energy_refurbishment_measure_energy_date_energy_date_of_event_energy_period_gml_time_period_gml_related_time{}.gml_time_node_gml_next_edge{}.gml_time_edge_gml_extent_gml_time_period_frame xml_buffer, energy_refurbishment_measure{}.energy_refurbishment_measure_energy_date_energy_date_of_event_energy_period_gml_time_period_gml_related_time{}.gml_time_node_gml_next_edge{}.gml_time_edge_gml_extent_gml_time_period_gml_id xml_buffer, energy_refurbishment_measure{}.energy_refurbishment_measure_energy_date_energy_date_of_event_energy_period_gml_time_period_gml_related_time{}.gml_time_node_gml_position_xlink_href xml_buffer, energy_refurbishment_measure{}.energy_refurbishment_measure_energy_date_energy_date_of_event_energy_period_gml_time_period_gml_related_time{}.gml_time_node_gml_position_gml_time_instant_frame xml_buffer, energy_refurbishment_measure{}.energy_refurbishment_measure_energy_date_energy_date_of_event_energy_period_gml_time_period_gml_related_time{}.gml_time_node_gml_position_gml_time_instant_gml_id xml_buffer, energy_refurbishment_measure{}.energy_refurbishment_measure_energy_date_energy_date_of_event_energy_period_gml_time_period_gml_related_time{}.gml_time_node_gml_position_gml_time_instant_gml_related_time{} xml_xml, energy_refurbishment_measure{}.energy_refurbishment_measure_energy_date_energy_date_of_event_energy_period_gml_time_period_gml_related_time{}.gml_time_node_gml_position_gml_time_instant_gml_related_time{}.relativePosition xml_char(12), energy_refurbishment_measure{}.energy_refurbishment_measure_energy_date_energy_date_of_event_energy_period_gml_time_period_gml_related_time{}.gml_time_node_gml_position_gml_time_instant_gml_related_time{}.xlink_href xml_buffer, energy_refurbishment_measure{}.energy_refurbishment_measure_energy_date_energy_date_of_event_energy_period_gml_time_period_gml_related_time{}.gml_time_node_gml_position_gml_time_instant_gml_time_position xml_buffer, energy_refurbishment_measure{}.energy_refurbishment_measure_energy_date_energy_date_of_event_energy_period_gml_time_period_gml_related_time{}.gml_time_node_gml_position_gml_time_instant_gml_time_position_frame xml_buffer, energy_refurbishment_measure{}.energy_refurbishment_measure_energy_date_energy_date_of_event_energy_period_gml_time_period_gml_related_time{}.gml_time_node_gml_position_gml_time_instant_gml_time_position_calendarEraName xml_buffer, energy_refurbishment_measure{}.energy_refurbishment_measure_energy_date_energy_date_of_event_energy_period_gml_time_period_gml_related_time{}.gml_time_node_gml_position_gml_time_instant_gml_time_position_indeterminatePosition xml_char(7), energy_refurbishment_measure{}.energy_refurbishment_measure_energy_date_energy_date_of_event_energy_period_gml_time_period_gml_related_time{}.gml_time_period xml_xml, energy_refurbishment_measure{}.energy_refurbishment_measure_energy_date_energy_date_of_event_energy_period_gml_time_period_gml_related_time{}.gml_time_period_frame xml_buffer, energy_refurbishment_measure{}.energy_refurbishment_measure_energy_date_energy_date_of_event_energy_period_gml_time_period_gml_related_time{}.gml_time_period_gml_id xml_buffer, energy_refurbishment_measure{}.energy_refurbishment_measure_energy_date_energy_date_of_event_energy_period_gml_time_period_gml_begin_position xml_buffer, energy_refurbishment_measure{}.energy_refurbishment_measure_energy_date_energy_date_of_event_energy_period_gml_time_period_gml_begin_position_frame xml_buffer, energy_refurbishment_measure{}.energy_refurbishment_measure_energy_date_energy_date_of_event_energy_period_gml_time_period_gml_begin_position_calendarEraName xml_buffer, energy_refurbishment_measure{}.energy_refurbishment_measure_energy_date_energy_date_of_event_energy_period_gml_time_period_gml_begin_position_indeterminatePosition xml_char(7),
      energy_refurbishment_measure{}.energy_refurbishment_measure_energy_date_energy_date_of_event_energy_period_gml_time_period_gml_begin_xlink_href xml_buffer, energy_refurbishment_measure{}.energy_refurbishment_measure_energy_date_energy_date_of_event_energy_period_gml_time_period_gml_begin_gml_time_instant_frame xml_buffer, energy_refurbishment_measure{}.energy_refurbishment_measure_energy_date_energy_date_of_event_energy_period_gml_time_period_gml_begin_gml_time_instant_gml_id xml_buffer, energy_refurbishment_measure{}.energy_refurbishment_measure_energy_date_energy_date_of_event_energy_period_gml_time_period_gml_begin_gml_time_instant_gml_related_time{}.relativePosition xml_char(12), energy_refurbishment_measure{}.energy_refurbishment_measure_energy_date_energy_date_of_event_energy_period_gml_time_period_gml_begin_gml_time_instant_gml_related_time{}.xlink_href xml_buffer, energy_refurbishment_measure{}.energy_refurbishment_measure_energy_date_energy_date_of_event_energy_period_gml_time_period_gml_begin_gml_time_instant_gml_related_time{}.gml_time_edge_gml_id xml_buffer, energy_refurbishment_measure{}.energy_refurbishment_measure_energy_date_energy_date_of_event_energy_period_gml_time_period_gml_begin_gml_time_instant_gml_related_time{}.gml_time_edge_gml_related_time{} xml_xml, energy_refurbishment_measure{}.energy_refurbishment_measure_energy_date_energy_date_of_event_energy_period_gml_time_period_gml_begin_gml_time_instant_gml_related_time{}.gml_time_edge_gml_related_time{}.relativePosition xml_char(12), energy_refurbishment_measure{}.energy_refurbishment_measure_energy_date_energy_date_of_event_energy_period_gml_time_period_gml_begin_gml_time_instant_gml_related_time{}.gml_time_edge_gml_related_time{}.xlink_href xml_buffer, energy_refurbishment_measure{}.energy_refurbishment_measure_energy_date_energy_date_of_event_energy_period_gml_time_period_gml_begin_gml_time_instant_gml_related_time{}.gml_time_edge_gml_complex_xlink_href xml_buffer, energy_refurbishment_measure{}.energy_refurbishment_measure_energy_date_energy_date_of_event_energy_period_gml_time_period_gml_begin_gml_time_instant_gml_related_time{}.gml_time_edge_gml_start_xlink_href xml_buffer, energy_refurbishment_measure{}.energy_refurbishment_measure_energy_date_energy_date_of_event_energy_period_gml_time_period_gml_begin_gml_time_instant_gml_related_time{}.gml_time_edge_gml_start_gml_time_node_gml_id xml_buffer, energy_refurbishment_measure{}.energy_refurbishment_measure_energy_date_energy_date_of_event_energy_period_gml_time_period_gml_begin_gml_time_instant_gml_related_time{}.gml_time_edge_gml_start_gml_time_node_gml_related_time{} xml_xml, energy_refurbishment_measure{}.energy_refurbishment_measure_energy_date_energy_date_of_event_energy_period_gml_time_period_gml_begin_gml_time_instant_gml_related_time{}.gml_time_edge_gml_start_gml_time_node_gml_related_time{}.relativePosition xml_char(12), energy_refurbishment_measure{}.energy_refurbishment_measure_energy_date_energy_date_of_event_energy_period_gml_time_period_gml_begin_gml_time_instant_gml_related_time{}.gml_time_edge_gml_start_gml_time_node_gml_related_time{}.xlink_href xml_buffer, energy_refurbishment_measure{}.energy_refurbishment_measure_energy_date_energy_date_of_event_energy_period_gml_time_period_gml_begin_gml_time_instant_gml_related_time{}.gml_time_edge_gml_start_gml_time_node_gml_complex_xlink_href xml_buffer, energy_refurbishment_measure{}.energy_refurbishment_measure_energy_date_energy_date_of_event_energy_period_gml_time_period_gml_begin_gml_time_instant_gml_related_time{}.gml_time_edge_gml_start_gml_time_node_gml_previous_edge{}.xlink_href xml_buffer, energy_refurbishment_measure{}.energy_refurbishment_measure_energy_date_energy_date_of_event_energy_period_gml_time_period_gml_begin_gml_time_instant_gml_related_time{}.gml_time_edge_gml_start_gml_time_node_gml_previous_edge{}.gml_time_edge xml_xml, energy_refurbishment_measure{}.energy_refurbishment_measure_energy_date_energy_date_of_event_energy_period_gml_time_period_gml_begin_gml_time_instant_gml_related_time{}.gml_time_edge_gml_start_gml_time_node_gml_previous_edge{}.gml_time_edge_gml_id xml_buffer, energy_refurbishment_measure{}.energy_refurbishment_measure_energy_date_energy_date_of_event_energy_period_gml_time_period_gml_begin_gml_time_instant_gml_related_time{}.gml_time_edge_gml_start_gml_time_node_gml_next_edge{}.xlink_href xml_buffer, energy_refurbishment_measure{}.energy_refurbishment_measure_energy_date_energy_date_of_event_energy_period_gml_time_period_gml_begin_gml_time_instant_gml_related_time{}.gml_time_edge_gml_start_gml_time_node_gml_next_edge{}.gml_time_edge xml_xml, energy_refurbishment_measure{}.energy_refurbishment_measure_energy_date_energy_date_of_event_energy_period_gml_time_period_gml_begin_gml_time_instant_gml_related_time{}.gml_time_edge_gml_start_gml_time_node_gml_next_edge{}.gml_time_edge_gml_id xml_buffer, energy_refurbishment_measure{}.energy_refurbishment_measure_energy_date_energy_date_of_event_energy_period_gml_time_period_gml_begin_gml_time_instant_gml_related_time{}.gml_time_edge_gml_start_gml_time_node_gml_position_xlink_href xml_buffer, energy_refurbishment_measure{}.energy_refurbishment_measure_energy_date_energy_date_of_event_energy_period_gml_time_period_gml_begin_gml_time_instant_gml_related_time{}.gml_time_edge_gml_start_gml_time_node_gml_position_gml_time_instant xml_xml, energy_refurbishment_measure{}.energy_refurbishment_measure_energy_date_energy_date_of_event_energy_period_gml_time_period_gml_begin_gml_time_instant_gml_related_time{}.gml_time_edge_gml_start_gml_time_node_gml_position_gml_time_instant_frame xml_buffer, energy_refurbishment_measure{}.energy_refurbishment_measure_energy_date_energy_date_of_event_energy_period_gml_time_period_gml_begin_gml_time_instant_gml_related_time{}.gml_time_edge_gml_start_gml_time_node_gml_position_gml_time_instant_gml_id xml_buffer, energy_refurbishment_measure{}.energy_refurbishment_measure_energy_date_energy_date_of_event_energy_period_gml_time_period_gml_begin_gml_time_instant_gml_related_time{}.gml_time_edge_gml_end_xlink_href xml_buffer, energy_refurbishment_measure{}.energy_refurbishment_measure_energy_date_energy_date_of_event_energy_period_gml_time_period_gml_begin_gml_time_instant_gml_related_time{}.gml_time_edge_gml_end_gml_time_node_gml_id xml_buffer, energy_refurbishment_measure{}.energy_refurbishment_measure_energy_date_energy_date_of_event_energy_period_gml_time_period_gml_begin_gml_time_instant_gml_related_time{}.gml_time_edge_gml_end_gml_time_node_gml_related_time{} xml_xml, energy_refurbishment_measure{}.energy_refurbishment_measure_energy_date_energy_date_of_event_energy_period_gml_time_period_gml_begin_gml_time_instant_gml_related_time{}.gml_time_edge_gml_end_gml_time_node_gml_related_time{}.relativePosition xml_char(12),
      energy_refurbishment_measure{}.energy_refurbishment_measure_energy_date_energy_date_of_event_energy_period_gml_time_period_gml_begin_gml_time_instant_gml_related_time{}.gml_time_edge_gml_end_gml_time_node_gml_related_time{}.xlink_href xml_buffer, energy_refurbishment_measure{}.energy_refurbishment_measure_energy_date_energy_date_of_event_energy_period_gml_time_period_gml_begin_gml_time_instant_gml_related_time{}.gml_time_edge_gml_end_gml_time_node_gml_complex_xlink_href xml_buffer, energy_refurbishment_measure{}.energy_refurbishment_measure_energy_date_energy_date_of_event_energy_period_gml_time_period_gml_begin_gml_time_instant_gml_related_time{}.gml_time_edge_gml_end_gml_time_node_gml_previous_edge{}.xlink_href xml_buffer, energy_refurbishment_measure{}.energy_refurbishment_measure_energy_date_energy_date_of_event_energy_period_gml_time_period_gml_begin_gml_time_instant_gml_related_time{}.gml_time_edge_gml_end_gml_time_node_gml_previous_edge{}.gml_time_edge xml_xml, energy_refurbishment_measure{}.energy_refurbishment_measure_energy_date_energy_date_of_event_energy_period_gml_time_period_gml_begin_gml_time_instant_gml_related_time{}.gml_time_edge_gml_end_gml_time_node_gml_previous_edge{}.gml_time_edge_gml_id xml_buffer, energy_refurbishment_measure{}.energy_refurbishment_measure_energy_date_energy_date_of_event_energy_period_gml_time_period_gml_begin_gml_time_instant_gml_related_time{}.gml_time_edge_gml_end_gml_time_node_gml_next_edge{}.xlink_href xml_buffer, energy_refurbishment_measure{}.energy_refurbishment_measure_energy_date_energy_date_of_event_energy_period_gml_time_period_gml_begin_gml_time_instant_gml_related_time{}.gml_time_edge_gml_end_gml_time_node_gml_next_edge{}.gml_time_edge xml_xml, energy_refurbishment_measure{}.energy_refurbishment_measure_energy_date_energy_date_of_event_energy_period_gml_time_period_gml_begin_gml_time_instant_gml_related_time{}.gml_time_edge_gml_end_gml_time_node_gml_next_edge{}.gml_time_edge_gml_id xml_buffer, energy_refurbishment_measure{}.energy_refurbishment_measure_energy_date_energy_date_of_event_energy_period_gml_time_period_gml_begin_gml_time_instant_gml_related_time{}.gml_time_edge_gml_end_gml_time_node_gml_position_xlink_href xml_buffer, energy_refurbishment_measure{}.energy_refurbishment_measure_energy_date_energy_date_of_event_energy_period_gml_time_period_gml_begin_gml_time_instant_gml_related_time{}.gml_time_edge_gml_end_gml_time_node_gml_position_gml_time_instant xml_xml, energy_refurbishment_measure{}.energy_refurbishment_measure_energy_date_energy_date_of_event_energy_period_gml_time_period_gml_begin_gml_time_instant_gml_related_time{}.gml_time_edge_gml_end_gml_time_node_gml_position_gml_time_instant_frame xml_buffer, energy_refurbishment_measure{}.energy_refurbishment_measure_energy_date_energy_date_of_event_energy_period_gml_time_period_gml_begin_gml_time_instant_gml_related_time{}.gml_time_edge_gml_end_gml_time_node_gml_position_gml_time_instant_gml_id xml_buffer, energy_refurbishment_measure{}.energy_refurbishment_measure_energy_date_energy_date_of_event_energy_period_gml_time_period_gml_begin_gml_time_instant_gml_related_time{}.gml_time_edge_gml_extent_xlink_href xml_buffer, energy_refurbishment_measure{}.energy_refurbishment_measure_energy_date_energy_date_of_event_energy_period_gml_time_period_gml_begin_gml_time_instant_gml_related_time{}.gml_time_edge_gml_extent_gml_time_period xml_xml, energy_refurbishment_measure{}.energy_refurbishment_measure_energy_date_energy_date_of_event_energy_period_gml_time_period_gml_begin_gml_time_instant_gml_related_time{}.gml_time_edge_gml_extent_gml_time_period_frame xml_buffer, energy_refurbishment_measure{}.energy_refurbishment_measure_energy_date_energy_date_of_event_energy_period_gml_time_period_gml_begin_gml_time_instant_gml_related_time{}.gml_time_edge_gml_extent_gml_time_period_gml_id xml_buffer, energy_refurbishment_measure{}.energy_refurbishment_measure_energy_date_energy_date_of_event_energy_period_gml_time_period_gml_begin_gml_time_instant_gml_related_time{}.gml_time_instant xml_xml, energy_refurbishment_measure{}.energy_refurbishment_measure_energy_date_energy_date_of_event_energy_period_gml_time_period_gml_begin_gml_time_instant_gml_related_time{}.gml_time_instant_frame xml_buffer, energy_refurbishment_measure{}.energy_refurbishment_measure_energy_date_energy_date_of_event_energy_period_gml_time_period_gml_begin_gml_time_instant_gml_related_time{}.gml_time_instant_gml_id xml_buffer, energy_refurbishment_measure{}.energy_refurbishment_measure_energy_date_energy_date_of_event_energy_period_gml_time_period_gml_begin_gml_time_instant_gml_related_time{}.gml_time_node_gml_id xml_buffer, energy_refurbishment_measure{}.energy_refurbishment_measure_energy_date_energy_date_of_event_energy_period_gml_time_period_gml_begin_gml_time_instant_gml_related_time{}.gml_time_node_gml_related_time{} xml_xml, energy_refurbishment_measure{}.energy_refurbishment_measure_energy_date_energy_date_of_event_energy_period_gml_time_period_gml_begin_gml_time_instant_gml_related_time{}.gml_time_node_gml_related_time{}.relativePosition xml_char(12), energy_refurbishment_measure{}.energy_refurbishment_measure_energy_date_energy_date_of_event_energy_period_gml_time_period_gml_begin_gml_time_instant_gml_related_time{}.gml_time_node_gml_related_time{}.xlink_href xml_buffer, energy_refurbishment_measure{}.energy_refurbishment_measure_energy_date_energy_date_of_event_energy_period_gml_time_period_gml_begin_gml_time_instant_gml_related_time{}.gml_time_node_gml_complex_xlink_href xml_buffer, energy_refurbishment_measure{}.energy_refurbishment_measure_energy_date_energy_date_of_event_energy_period_gml_time_period_gml_begin_gml_time_instant_gml_related_time{}.gml_time_node_gml_previous_edge{}.xlink_href xml_buffer, energy_refurbishment_measure{}.energy_refurbishment_measure_energy_date_energy_date_of_event_energy_period_gml_time_period_gml_begin_gml_time_instant_gml_related_time{}.gml_time_node_gml_previous_edge{}.gml_time_edge_gml_id xml_buffer, energy_refurbishment_measure{}.energy_refurbishment_measure_energy_date_energy_date_of_event_energy_period_gml_time_period_gml_begin_gml_time_instant_gml_related_time{}.gml_time_node_gml_previous_edge{}.gml_time_edge_gml_related_time{} xml_xml, energy_refurbishment_measure{}.energy_refurbishment_measure_energy_date_energy_date_of_event_energy_period_gml_time_period_gml_begin_gml_time_instant_gml_related_time{}.gml_time_node_gml_previous_edge{}.gml_time_edge_gml_related_time{}.relativePosition xml_char(12), energy_refurbishment_measure{}.energy_refurbishment_measure_energy_date_energy_date_of_event_energy_period_gml_time_period_gml_begin_gml_time_instant_gml_related_time{}.gml_time_node_gml_previous_edge{}.gml_time_edge_gml_related_time{}.xlink_href xml_buffer, energy_refurbishment_measure{}.energy_refurbishment_measure_energy_date_energy_date_of_event_energy_period_gml_time_period_gml_begin_gml_time_instant_gml_related_time{}.gml_time_node_gml_previous_edge{}.gml_time_edge_gml_complex_xlink_href xml_buffer,
      energy_refurbishment_measure{}.energy_refurbishment_measure_energy_date_energy_date_of_event_energy_period_gml_time_period_gml_begin_gml_time_instant_gml_related_time{}.gml_time_node_gml_previous_edge{}.gml_time_edge_gml_start_xlink_href xml_buffer, energy_refurbishment_measure{}.energy_refurbishment_measure_energy_date_energy_date_of_event_energy_period_gml_time_period_gml_begin_gml_time_instant_gml_related_time{}.gml_time_node_gml_previous_edge{}.gml_time_edge_gml_start_gml_time_node xml_xml, energy_refurbishment_measure{}.energy_refurbishment_measure_energy_date_energy_date_of_event_energy_period_gml_time_period_gml_begin_gml_time_instant_gml_related_time{}.gml_time_node_gml_previous_edge{}.gml_time_edge_gml_start_gml_time_node_gml_id xml_buffer, energy_refurbishment_measure{}.energy_refurbishment_measure_energy_date_energy_date_of_event_energy_period_gml_time_period_gml_begin_gml_time_instant_gml_related_time{}.gml_time_node_gml_previous_edge{}.gml_time_edge_gml_end_xlink_href xml_buffer, energy_refurbishment_measure{}.energy_refurbishment_measure_energy_date_energy_date_of_event_energy_period_gml_time_period_gml_begin_gml_time_instant_gml_related_time{}.gml_time_node_gml_previous_edge{}.gml_time_edge_gml_end_gml_time_node xml_xml, energy_refurbishment_measure{}.energy_refurbishment_measure_energy_date_energy_date_of_event_energy_period_gml_time_period_gml_begin_gml_time_instant_gml_related_time{}.gml_time_node_gml_previous_edge{}.gml_time_edge_gml_end_gml_time_node_gml_id xml_buffer, energy_refurbishment_measure{}.energy_refurbishment_measure_energy_date_energy_date_of_event_energy_period_gml_time_period_gml_begin_gml_time_instant_gml_related_time{}.gml_time_node_gml_previous_edge{}.gml_time_edge_gml_extent_xlink_href xml_buffer, energy_refurbishment_measure{}.energy_refurbishment_measure_energy_date_energy_date_of_event_energy_period_gml_time_period_gml_begin_gml_time_instant_gml_related_time{}.gml_time_node_gml_previous_edge{}.gml_time_edge_gml_extent_gml_time_period xml_xml, energy_refurbishment_measure{}.energy_refurbishment_measure_energy_date_energy_date_of_event_energy_period_gml_time_period_gml_begin_gml_time_instant_gml_related_time{}.gml_time_node_gml_previous_edge{}.gml_time_edge_gml_extent_gml_time_period_frame xml_buffer, energy_refurbishment_measure{}.energy_refurbishment_measure_energy_date_energy_date_of_event_energy_period_gml_time_period_gml_begin_gml_time_instant_gml_related_time{}.gml_time_node_gml_previous_edge{}.gml_time_edge_gml_extent_gml_time_period_gml_id xml_buffer, energy_refurbishment_measure{}.energy_refurbishment_measure_energy_date_energy_date_of_event_energy_period_gml_time_period_gml_begin_gml_time_instant_gml_related_time{}.gml_time_node_gml_next_edge{}.xlink_href xml_buffer, energy_refurbishment_measure{}.energy_refurbishment_measure_energy_date_energy_date_of_event_energy_period_gml_time_period_gml_begin_gml_time_instant_gml_related_time{}.gml_time_node_gml_next_edge{}.gml_time_edge_gml_id xml_buffer, energy_refurbishment_measure{}.energy_refurbishment_measure_energy_date_energy_date_of_event_energy_period_gml_time_period_gml_begin_gml_time_instant_gml_related_time{}.gml_time_node_gml_next_edge{}.gml_time_edge_gml_related_time{} xml_xml, energy_refurbishment_measure{}.energy_refurbishment_measure_energy_date_energy_date_of_event_energy_period_gml_time_period_gml_begin_gml_time_instant_gml_related_time{}.gml_time_node_gml_next_edge{}.gml_time_edge_gml_related_time{}.relativePosition xml_char(12), energy_refurbishment_measure{}.energy_refurbishment_measure_energy_date_energy_date_of_event_energy_period_gml_time_period_gml_begin_gml_time_instant_gml_related_time{}.gml_time_node_gml_next_edge{}.gml_time_edge_gml_related_time{}.xlink_href xml_buffer, energy_refurbishment_measure{}.energy_refurbishment_measure_energy_date_energy_date_of_event_energy_period_gml_time_period_gml_begin_gml_time_instant_gml_related_time{}.gml_time_node_gml_next_edge{}.gml_time_edge_gml_complex_xlink_href xml_buffer, energy_refurbishment_measure{}.energy_refurbishment_measure_energy_date_energy_date_of_event_energy_period_gml_time_period_gml_begin_gml_time_instant_gml_related_time{}.gml_time_node_gml_next_edge{}.gml_time_edge_gml_start_xlink_href xml_buffer, energy_refurbishment_measure{}.energy_refurbishment_measure_energy_date_energy_date_of_event_energy_period_gml_time_period_gml_begin_gml_time_instant_gml_related_time{}.gml_time_node_gml_next_edge{}.gml_time_edge_gml_start_gml_time_node xml_xml, energy_refurbishment_measure{}.energy_refurbishment_measure_energy_date_energy_date_of_event_energy_period_gml_time_period_gml_begin_gml_time_instant_gml_related_time{}.gml_time_node_gml_next_edge{}.gml_time_edge_gml_start_gml_time_node_gml_id xml_buffer, energy_refurbishment_measure{}.energy_refurbishment_measure_energy_date_energy_date_of_event_energy_period_gml_time_period_gml_begin_gml_time_instant_gml_related_time{}.gml_time_node_gml_next_edge{}.gml_time_edge_gml_end_xlink_href xml_buffer, energy_refurbishment_measure{}.energy_refurbishment_measure_energy_date_energy_date_of_event_energy_period_gml_time_period_gml_begin_gml_time_instant_gml_related_time{}.gml_time_node_gml_next_edge{}.gml_time_edge_gml_end_gml_time_node xml_xml, energy_refurbishment_measure{}.energy_refurbishment_measure_energy_date_energy_date_of_event_energy_period_gml_time_period_gml_begin_gml_time_instant_gml_related_time{}.gml_time_node_gml_next_edge{}.gml_time_edge_gml_end_gml_time_node_gml_id xml_buffer, energy_refurbishment_measure{}.energy_refurbishment_measure_energy_date_energy_date_of_event_energy_period_gml_time_period_gml_begin_gml_time_instant_gml_related_time{}.gml_time_node_gml_next_edge{}.gml_time_edge_gml_extent_xlink_href xml_buffer, energy_refurbishment_measure{}.energy_refurbishment_measure_energy_date_energy_date_of_event_energy_period_gml_time_period_gml_begin_gml_time_instant_gml_related_time{}.gml_time_node_gml_next_edge{}.gml_time_edge_gml_extent_gml_time_period xml_xml, energy_refurbishment_measure{}.energy_refurbishment_measure_energy_date_energy_date_of_event_energy_period_gml_time_period_gml_begin_gml_time_instant_gml_related_time{}.gml_time_node_gml_next_edge{}.gml_time_edge_gml_extent_gml_time_period_frame xml_buffer, energy_refurbishment_measure{}.energy_refurbishment_measure_energy_date_energy_date_of_event_energy_period_gml_time_period_gml_begin_gml_time_instant_gml_related_time{}.gml_time_node_gml_next_edge{}.gml_time_edge_gml_extent_gml_time_period_gml_id xml_buffer, energy_refurbishment_measure{}.energy_refurbishment_measure_energy_date_energy_date_of_event_energy_period_gml_time_period_gml_begin_gml_time_instant_gml_related_time{}.gml_time_node_gml_position_xlink_href xml_buffer, energy_refurbishment_measure{}.energy_refurbishment_measure_energy_date_energy_date_of_event_energy_period_gml_time_period_gml_begin_gml_time_instant_gml_related_time{}.gml_time_node_gml_position_gml_time_instant xml_xml, energy_refurbishment_measure{}.energy_refurbishment_measure_energy_date_energy_date_of_event_energy_period_gml_time_period_gml_begin_gml_time_instant_gml_related_time{}.gml_time_node_gml_position_gml_time_instant_frame xml_buffer, energy_refurbishment_measure{}.energy_refurbishment_measure_energy_date_energy_date_of_event_energy_period_gml_time_period_gml_begin_gml_time_instant_gml_related_time{}.gml_time_node_gml_position_gml_time_instant_gml_id xml_buffer,
      energy_refurbishment_measure{}.energy_refurbishment_measure_energy_date_energy_date_of_event_energy_period_gml_time_period_gml_begin_gml_time_instant_gml_related_time{}.gml_time_period xml_xml, energy_refurbishment_measure{}.energy_refurbishment_measure_energy_date_energy_date_of_event_energy_period_gml_time_period_gml_begin_gml_time_instant_gml_related_time{}.gml_time_period_frame xml_buffer, energy_refurbishment_measure{}.energy_refurbishment_measure_energy_date_energy_date_of_event_energy_period_gml_time_period_gml_begin_gml_time_instant_gml_related_time{}.gml_time_period_gml_id xml_buffer, energy_refurbishment_measure{}.energy_refurbishment_measure_energy_date_energy_date_of_event_energy_period_gml_time_period_gml_begin_gml_time_instant_gml_time_position xml_buffer, energy_refurbishment_measure{}.energy_refurbishment_measure_energy_date_energy_date_of_event_energy_period_gml_time_period_gml_begin_gml_time_instant_gml_time_position_frame xml_buffer, energy_refurbishment_measure{}.energy_refurbishment_measure_energy_date_energy_date_of_event_energy_period_gml_time_period_gml_begin_gml_time_instant_gml_time_position_calendarEraName xml_buffer, energy_refurbishment_measure{}.energy_refurbishment_measure_energy_date_energy_date_of_event_energy_period_gml_time_period_gml_begin_gml_time_instant_gml_time_position_indeterminatePosition xml_char(7), energy_refurbishment_measure{}.energy_refurbishment_measure_energy_date_energy_date_of_event_energy_period_gml_time_period_gml_end_position xml_buffer, energy_refurbishment_measure{}.energy_refurbishment_measure_energy_date_energy_date_of_event_energy_period_gml_time_period_gml_end_position_frame xml_buffer, energy_refurbishment_measure{}.energy_refurbishment_measure_energy_date_energy_date_of_event_energy_period_gml_time_period_gml_end_position_calendarEraName xml_buffer, energy_refurbishment_measure{}.energy_refurbishment_measure_energy_date_energy_date_of_event_energy_period_gml_time_period_gml_end_position_indeterminatePosition xml_char(7), energy_refurbishment_measure{}.energy_refurbishment_measure_energy_date_energy_date_of_event_energy_period_gml_time_period_gml_end_xlink_href xml_buffer, energy_refurbishment_measure{}.energy_refurbishment_measure_energy_date_energy_date_of_event_energy_period_gml_time_period_gml_end_gml_time_instant_frame xml_buffer, energy_refurbishment_measure{}.energy_refurbishment_measure_energy_date_energy_date_of_event_energy_period_gml_time_period_gml_end_gml_time_instant_gml_id xml_buffer, energy_refurbishment_measure{}.energy_refurbishment_measure_energy_date_energy_date_of_event_energy_period_gml_time_period_gml_end_gml_time_instant_gml_related_time{}.relativePosition xml_char(12), energy_refurbishment_measure{}.energy_refurbishment_measure_energy_date_energy_date_of_event_energy_period_gml_time_period_gml_end_gml_time_instant_gml_related_time{}.xlink_href xml_buffer, energy_refurbishment_measure{}.energy_refurbishment_measure_energy_date_energy_date_of_event_energy_period_gml_time_period_gml_end_gml_time_instant_gml_related_time{}.gml_time_edge_gml_id xml_buffer, energy_refurbishment_measure{}.energy_refurbishment_measure_energy_date_energy_date_of_event_energy_period_gml_time_period_gml_end_gml_time_instant_gml_related_time{}.gml_time_edge_gml_related_time{} xml_xml, energy_refurbishment_measure{}.energy_refurbishment_measure_energy_date_energy_date_of_event_energy_period_gml_time_period_gml_end_gml_time_instant_gml_related_time{}.gml_time_edge_gml_related_time{}.relativePosition xml_char(12), energy_refurbishment_measure{}.energy_refurbishment_measure_energy_date_energy_date_of_event_energy_period_gml_time_period_gml_end_gml_time_instant_gml_related_time{}.gml_time_edge_gml_related_time{}.xlink_href xml_buffer, energy_refurbishment_measure{}.energy_refurbishment_measure_energy_date_energy_date_of_event_energy_period_gml_time_period_gml_end_gml_time_instant_gml_related_time{}.gml_time_edge_gml_complex_xlink_href xml_buffer, energy_refurbishment_measure{}.energy_refurbishment_measure_energy_date_energy_date_of_event_energy_period_gml_time_period_gml_end_gml_time_instant_gml_related_time{}.gml_time_edge_gml_start_xlink_href xml_buffer, energy_refurbishment_measure{}.energy_refurbishment_measure_energy_date_energy_date_of_event_energy_period_gml_time_period_gml_end_gml_time_instant_gml_related_time{}.gml_time_edge_gml_start_gml_time_node_gml_id xml_buffer, energy_refurbishment_measure{}.energy_refurbishment_measure_energy_date_energy_date_of_event_energy_period_gml_time_period_gml_end_gml_time_instant_gml_related_time{}.gml_time_edge_gml_start_gml_time_node_gml_related_time{} xml_xml, energy_refurbishment_measure{}.energy_refurbishment_measure_energy_date_energy_date_of_event_energy_period_gml_time_period_gml_end_gml_time_instant_gml_related_time{}.gml_time_edge_gml_start_gml_time_node_gml_related_time{}.relativePosition xml_char(12), energy_refurbishment_measure{}.energy_refurbishment_measure_energy_date_energy_date_of_event_energy_period_gml_time_period_gml_end_gml_time_instant_gml_related_time{}.gml_time_edge_gml_start_gml_time_node_gml_related_time{}.xlink_href xml_buffer, energy_refurbishment_measure{}.energy_refurbishment_measure_energy_date_energy_date_of_event_energy_period_gml_time_period_gml_end_gml_time_instant_gml_related_time{}.gml_time_edge_gml_start_gml_time_node_gml_complex_xlink_href xml_buffer, energy_refurbishment_measure{}.energy_refurbishment_measure_energy_date_energy_date_of_event_energy_period_gml_time_period_gml_end_gml_time_instant_gml_related_time{}.gml_time_edge_gml_start_gml_time_node_gml_previous_edge{}.xlink_href xml_buffer, energy_refurbishment_measure{}.energy_refurbishment_measure_energy_date_energy_date_of_event_energy_period_gml_time_period_gml_end_gml_time_instant_gml_related_time{}.gml_time_edge_gml_start_gml_time_node_gml_previous_edge{}.gml_time_edge xml_xml, energy_refurbishment_measure{}.energy_refurbishment_measure_energy_date_energy_date_of_event_energy_period_gml_time_period_gml_end_gml_time_instant_gml_related_time{}.gml_time_edge_gml_start_gml_time_node_gml_previous_edge{}.gml_time_edge_gml_id xml_buffer,
      energy_refurbishment_measure{}.energy_refurbishment_measure_energy_date_energy_date_of_event_energy_period_gml_time_period_gml_end_gml_time_instant_gml_related_time{}.gml_time_edge_gml_start_gml_time_node_gml_next_edge{}.xlink_href xml_buffer, energy_refurbishment_measure{}.energy_refurbishment_measure_energy_date_energy_date_of_event_energy_period_gml_time_period_gml_end_gml_time_instant_gml_related_time{}.gml_time_edge_gml_start_gml_time_node_gml_next_edge{}.gml_time_edge xml_xml, energy_refurbishment_measure{}.energy_refurbishment_measure_energy_date_energy_date_of_event_energy_period_gml_time_period_gml_end_gml_time_instant_gml_related_time{}.gml_time_edge_gml_start_gml_time_node_gml_next_edge{}.gml_time_edge_gml_id xml_buffer, energy_refurbishment_measure{}.energy_refurbishment_measure_energy_date_energy_date_of_event_energy_period_gml_time_period_gml_end_gml_time_instant_gml_related_time{}.gml_time_edge_gml_start_gml_time_node_gml_position_xlink_href xml_buffer, energy_refurbishment_measure{}.energy_refurbishment_measure_energy_date_energy_date_of_event_energy_period_gml_time_period_gml_end_gml_time_instant_gml_related_time{}.gml_time_edge_gml_start_gml_time_node_gml_position_gml_time_instant xml_xml, energy_refurbishment_measure{}.energy_refurbishment_measure_energy_date_energy_date_of_event_energy_period_gml_time_period_gml_end_gml_time_instant_gml_related_time{}.gml_time_edge_gml_start_gml_time_node_gml_position_gml_time_instant_frame xml_buffer, energy_refurbishment_measure{}.energy_refurbishment_measure_energy_date_energy_date_of_event_energy_period_gml_time_period_gml_end_gml_time_instant_gml_related_time{}.gml_time_edge_gml_start_gml_time_node_gml_position_gml_time_instant_gml_id xml_buffer, energy_refurbishment_measure{}.energy_refurbishment_measure_energy_date_energy_date_of_event_energy_period_gml_time_period_gml_end_gml_time_instant_gml_related_time{}.gml_time_edge_gml_end_xlink_href xml_buffer, energy_refurbishment_measure{}.energy_refurbishment_measure_energy_date_energy_date_of_event_energy_period_gml_time_period_gml_end_gml_time_instant_gml_related_time{}.gml_time_edge_gml_end_gml_time_node_gml_id xml_buffer, energy_refurbishment_measure{}.energy_refurbishment_measure_energy_date_energy_date_of_event_energy_period_gml_time_period_gml_end_gml_time_instant_gml_related_time{}.gml_time_edge_gml_end_gml_time_node_gml_related_time{} xml_xml, energy_refurbishment_measure{}.energy_refurbishment_measure_energy_date_energy_date_of_event_energy_period_gml_time_period_gml_end_gml_time_instant_gml_related_time{}.gml_time_edge_gml_end_gml_time_node_gml_related_time{}.relativePosition xml_char(12), energy_refurbishment_measure{}.energy_refurbishment_measure_energy_date_energy_date_of_event_energy_period_gml_time_period_gml_end_gml_time_instant_gml_related_time{}.gml_time_edge_gml_end_gml_time_node_gml_related_time{}.xlink_href xml_buffer, energy_refurbishment_measure{}.energy_refurbishment_measure_energy_date_energy_date_of_event_energy_period_gml_time_period_gml_end_gml_time_instant_gml_related_time{}.gml_time_edge_gml_end_gml_time_node_gml_complex_xlink_href xml_buffer, energy_refurbishment_measure{}.energy_refurbishment_measure_energy_date_energy_date_of_event_energy_period_gml_time_period_gml_end_gml_time_instant_gml_related_time{}.gml_time_edge_gml_end_gml_time_node_gml_previous_edge{}.xlink_href xml_buffer, energy_refurbishment_measure{}.energy_refurbishment_measure_energy_date_energy_date_of_event_energy_period_gml_time_period_gml_end_gml_time_instant_gml_related_time{}.gml_time_edge_gml_end_gml_time_node_gml_previous_edge{}.gml_time_edge xml_xml, energy_refurbishment_measure{}.energy_refurbishment_measure_energy_date_energy_date_of_event_energy_period_gml_time_period_gml_end_gml_time_instant_gml_related_time{}.gml_time_edge_gml_end_gml_time_node_gml_previous_edge{}.gml_time_edge_gml_id xml_buffer, energy_refurbishment_measure{}.energy_refurbishment_measure_energy_date_energy_date_of_event_energy_period_gml_time_period_gml_end_gml_time_instant_gml_related_time{}.gml_time_edge_gml_end_gml_time_node_gml_next_edge{}.xlink_href xml_buffer, energy_refurbishment_measure{}.energy_refurbishment_measure_energy_date_energy_date_of_event_energy_period_gml_time_period_gml_end_gml_time_instant_gml_related_time{}.gml_time_edge_gml_end_gml_time_node_gml_next_edge{}.gml_time_edge xml_xml, energy_refurbishment_measure{}.energy_refurbishment_measure_energy_date_energy_date_of_event_energy_period_gml_time_period_gml_end_gml_time_instant_gml_related_time{}.gml_time_edge_gml_end_gml_time_node_gml_next_edge{}.gml_time_edge_gml_id xml_buffer, energy_refurbishment_measure{}.energy_refurbishment_measure_energy_date_energy_date_of_event_energy_period_gml_time_period_gml_end_gml_time_instant_gml_related_time{}.gml_time_edge_gml_end_gml_time_node_gml_position_xlink_href xml_buffer, energy_refurbishment_measure{}.energy_refurbishment_measure_energy_date_energy_date_of_event_energy_period_gml_time_period_gml_end_gml_time_instant_gml_related_time{}.gml_time_edge_gml_end_gml_time_node_gml_position_gml_time_instant xml_xml, energy_refurbishment_measure{}.energy_refurbishment_measure_energy_date_energy_date_of_event_energy_period_gml_time_period_gml_end_gml_time_instant_gml_related_time{}.gml_time_edge_gml_end_gml_time_node_gml_position_gml_time_instant_frame xml_buffer, energy_refurbishment_measure{}.energy_refurbishment_measure_energy_date_energy_date_of_event_energy_period_gml_time_period_gml_end_gml_time_instant_gml_related_time{}.gml_time_edge_gml_end_gml_time_node_gml_position_gml_time_instant_gml_id xml_buffer, energy_refurbishment_measure{}.energy_refurbishment_measure_energy_date_energy_date_of_event_energy_period_gml_time_period_gml_end_gml_time_instant_gml_related_time{}.gml_time_edge_gml_extent_xlink_href xml_buffer, energy_refurbishment_measure{}.energy_refurbishment_measure_energy_date_energy_date_of_event_energy_period_gml_time_period_gml_end_gml_time_instant_gml_related_time{}.gml_time_edge_gml_extent_gml_time_period xml_xml, energy_refurbishment_measure{}.energy_refurbishment_measure_energy_date_energy_date_of_event_energy_period_gml_time_period_gml_end_gml_time_instant_gml_related_time{}.gml_time_edge_gml_extent_gml_time_period_frame xml_buffer, energy_refurbishment_measure{}.energy_refurbishment_measure_energy_date_energy_date_of_event_energy_period_gml_time_period_gml_end_gml_time_instant_gml_related_time{}.gml_time_edge_gml_extent_gml_time_period_gml_id xml_buffer, energy_refurbishment_measure{}.energy_refurbishment_measure_energy_date_energy_date_of_event_energy_period_gml_time_period_gml_end_gml_time_instant_gml_related_time{}.gml_time_instant xml_xml, energy_refurbishment_measure{}.energy_refurbishment_measure_energy_date_energy_date_of_event_energy_period_gml_time_period_gml_end_gml_time_instant_gml_related_time{}.gml_time_instant_frame xml_buffer, energy_refurbishment_measure{}.energy_refurbishment_measure_energy_date_energy_date_of_event_energy_period_gml_time_period_gml_end_gml_time_instant_gml_related_time{}.gml_time_instant_gml_id xml_buffer,
      energy_refurbishment_measure{}.energy_refurbishment_measure_energy_date_energy_date_of_event_energy_period_gml_time_period_gml_end_gml_time_instant_gml_related_time{}.gml_time_node_gml_id xml_buffer, energy_refurbishment_measure{}.energy_refurbishment_measure_energy_date_energy_date_of_event_energy_period_gml_time_period_gml_end_gml_time_instant_gml_related_time{}.gml_time_node_gml_related_time{} xml_xml, energy_refurbishment_measure{}.energy_refurbishment_measure_energy_date_energy_date_of_event_energy_period_gml_time_period_gml_end_gml_time_instant_gml_related_time{}.gml_time_node_gml_related_time{}.relativePosition xml_char(12), energy_refurbishment_measure{}.energy_refurbishment_measure_energy_date_energy_date_of_event_energy_period_gml_time_period_gml_end_gml_time_instant_gml_related_time{}.gml_time_node_gml_related_time{}.xlink_href xml_buffer, energy_refurbishment_measure{}.energy_refurbishment_measure_energy_date_energy_date_of_event_energy_period_gml_time_period_gml_end_gml_time_instant_gml_related_time{}.gml_time_node_gml_complex_xlink_href xml_buffer, energy_refurbishment_measure{}.energy_refurbishment_measure_energy_date_energy_date_of_event_energy_period_gml_time_period_gml_end_gml_time_instant_gml_related_time{}.gml_time_node_gml_previous_edge{}.xlink_href xml_buffer, energy_refurbishment_measure{}.energy_refurbishment_measure_energy_date_energy_date_of_event_energy_period_gml_time_period_gml_end_gml_time_instant_gml_related_time{}.gml_time_node_gml_previous_edge{}.gml_time_edge_gml_id xml_buffer, energy_refurbishment_measure{}.energy_refurbishment_measure_energy_date_energy_date_of_event_energy_period_gml_time_period_gml_end_gml_time_instant_gml_related_time{}.gml_time_node_gml_previous_edge{}.gml_time_edge_gml_related_time{} xml_xml, energy_refurbishment_measure{}.energy_refurbishment_measure_energy_date_energy_date_of_event_energy_period_gml_time_period_gml_end_gml_time_instant_gml_related_time{}.gml_time_node_gml_previous_edge{}.gml_time_edge_gml_related_time{}.relativePosition xml_char(12), energy_refurbishment_measure{}.energy_refurbishment_measure_energy_date_energy_date_of_event_energy_period_gml_time_period_gml_end_gml_time_instant_gml_related_time{}.gml_time_node_gml_previous_edge{}.gml_time_edge_gml_related_time{}.xlink_href xml_buffer, energy_refurbishment_measure{}.energy_refurbishment_measure_energy_date_energy_date_of_event_energy_period_gml_time_period_gml_end_gml_time_instant_gml_related_time{}.gml_time_node_gml_previous_edge{}.gml_time_edge_gml_complex_xlink_href xml_buffer, energy_refurbishment_measure{}.energy_refurbishment_measure_energy_date_energy_date_of_event_energy_period_gml_time_period_gml_end_gml_time_instant_gml_related_time{}.gml_time_node_gml_previous_edge{}.gml_time_edge_gml_start_xlink_href xml_buffer, energy_refurbishment_measure{}.energy_refurbishment_measure_energy_date_energy_date_of_event_energy_period_gml_time_period_gml_end_gml_time_instant_gml_related_time{}.gml_time_node_gml_previous_edge{}.gml_time_edge_gml_start_gml_time_node xml_xml, energy_refurbishment_measure{}.energy_refurbishment_measure_energy_date_energy_date_of_event_energy_period_gml_time_period_gml_end_gml_time_instant_gml_related_time{}.gml_time_node_gml_previous_edge{}.gml_time_edge_gml_start_gml_time_node_gml_id xml_buffer, energy_refurbishment_measure{}.energy_refurbishment_measure_energy_date_energy_date_of_event_energy_period_gml_time_period_gml_end_gml_time_instant_gml_related_time{}.gml_time_node_gml_previous_edge{}.gml_time_edge_gml_end_xlink_href xml_buffer, energy_refurbishment_measure{}.energy_refurbishment_measure_energy_date_energy_date_of_event_energy_period_gml_time_period_gml_end_gml_time_instant_gml_related_time{}.gml_time_node_gml_previous_edge{}.gml_time_edge_gml_end_gml_time_node xml_xml, energy_refurbishment_measure{}.energy_refurbishment_measure_energy_date_energy_date_of_event_energy_period_gml_time_period_gml_end_gml_time_instant_gml_related_time{}.gml_time_node_gml_previous_edge{}.gml_time_edge_gml_end_gml_time_node_gml_id xml_buffer, energy_refurbishment_measure{}.energy_refurbishment_measure_energy_date_energy_date_of_event_energy_period_gml_time_period_gml_end_gml_time_instant_gml_related_time{}.gml_time_node_gml_previous_edge{}.gml_time_edge_gml_extent_xlink_href xml_buffer, energy_refurbishment_measure{}.energy_refurbishment_measure_energy_date_energy_date_of_event_energy_period_gml_time_period_gml_end_gml_time_instant_gml_related_time{}.gml_time_node_gml_previous_edge{}.gml_time_edge_gml_extent_gml_time_period xml_xml, energy_refurbishment_measure{}.energy_refurbishment_measure_energy_date_energy_date_of_event_energy_period_gml_time_period_gml_end_gml_time_instant_gml_related_time{}.gml_time_node_gml_previous_edge{}.gml_time_edge_gml_extent_gml_time_period_frame xml_buffer, energy_refurbishment_measure{}.energy_refurbishment_measure_energy_date_energy_date_of_event_energy_period_gml_time_period_gml_end_gml_time_instant_gml_related_time{}.gml_time_node_gml_previous_edge{}.gml_time_edge_gml_extent_gml_time_period_gml_id xml_buffer, energy_refurbishment_measure{}.energy_refurbishment_measure_energy_date_energy_date_of_event_energy_period_gml_time_period_gml_end_gml_time_instant_gml_related_time{}.gml_time_node_gml_next_edge{}.xlink_href xml_buffer, energy_refurbishment_measure{}.energy_refurbishment_measure_energy_date_energy_date_of_event_energy_period_gml_time_period_gml_end_gml_time_instant_gml_related_time{}.gml_time_node_gml_next_edge{}.gml_time_edge_gml_id xml_buffer, gml_description xml_buffer, gml_name xml_buffer, energy_refurbishment_measure{}.energy_refurbishment_measure_energy_date_energy_date_of_event_energy_period_gml_time_period_gml_end_gml_time_instant_gml_related_time{}.gml_time_node_gml_next_edge{}.gml_time_edge_gml_related_time{} xml_xml, energy_refurbishment_measure{}.energy_refurbishment_measure_energy_date_energy_date_of_event_energy_period_gml_time_period_gml_end_gml_time_instant_gml_related_time{}.gml_time_node_gml_next_edge{}.gml_time_edge_gml_related_time{}.relativePosition xml_char(12), energy_refurbishment_measure{}.energy_refurbishment_measure_energy_date_energy_date_of_event_energy_period_gml_time_period_gml_end_gml_time_instant_gml_related_time{}.gml_time_node_gml_next_edge{}.gml_time_edge_gml_related_time{}.xlink_href xml_buffer, energy_refurbishment_measure{}.energy_refurbishment_measure_energy_date_energy_date_of_event_energy_period_gml_time_period_gml_end_gml_time_instant_gml_related_time{}.gml_time_node_gml_next_edge{}.gml_time_edge_gml_complex_xlink_href xml_buffer, energy_refurbishment_measure{}.energy_refurbishment_measure_energy_date_energy_date_of_event_energy_period_gml_time_period_gml_end_gml_time_instant_gml_related_time{}.gml_time_node_gml_next_edge{}.gml_time_edge_gml_start_xlink_href xml_buffer,
      energy_refurbishment_measure{}.energy_refurbishment_measure_energy_date_energy_date_of_event_energy_period_gml_time_period_gml_end_gml_time_instant_gml_related_time{}.gml_time_node_gml_next_edge{}.gml_time_edge_gml_start_gml_time_node xml_xml, energy_refurbishment_measure{}.energy_refurbishment_measure_energy_date_energy_date_of_event_energy_period_gml_time_period_gml_end_gml_time_instant_gml_related_time{}.gml_time_node_gml_next_edge{}.gml_time_edge_gml_start_gml_time_node_gml_id xml_buffer, energy_refurbishment_measure{}.energy_refurbishment_measure_energy_date_energy_date_of_event_energy_period_gml_time_period_gml_end_gml_time_instant_gml_related_time{}.gml_time_node_gml_next_edge{}.gml_time_edge_gml_end_xlink_href xml_buffer, energy_refurbishment_measure{}.energy_refurbishment_measure_energy_date_energy_date_of_event_energy_period_gml_time_period_gml_end_gml_time_instant_gml_related_time{}.gml_time_node_gml_next_edge{}.gml_time_edge_gml_end_gml_time_node xml_xml, energy_refurbishment_measure{}.energy_refurbishment_measure_energy_date_energy_date_of_event_energy_period_gml_time_period_gml_end_gml_time_instant_gml_related_time{}.gml_time_node_gml_next_edge{}.gml_time_edge_gml_end_gml_time_node_gml_id xml_buffer, energy_refurbishment_measure{}.energy_refurbishment_measure_energy_date_energy_date_of_event_energy_period_gml_time_period_gml_end_gml_time_instant_gml_related_time{}.gml_time_node_gml_next_edge{}.gml_time_edge_gml_extent_xlink_href xml_buffer, energy_refurbishment_measure{}.energy_refurbishment_measure_energy_date_energy_date_of_event_energy_period_gml_time_period_gml_end_gml_time_instant_gml_related_time{}.gml_time_node_gml_next_edge{}.gml_time_edge_gml_extent_gml_time_period xml_xml, energy_refurbishment_measure{}.energy_refurbishment_measure_energy_date_energy_date_of_event_energy_period_gml_time_period_gml_end_gml_time_instant_gml_related_time{}.gml_time_node_gml_next_edge{}.gml_time_edge_gml_extent_gml_time_period_frame xml_buffer, energy_refurbishment_measure{}.energy_refurbishment_measure_energy_date_energy_date_of_event_energy_period_gml_time_period_gml_end_gml_time_instant_gml_related_time{}.gml_time_node_gml_next_edge{}.gml_time_edge_gml_extent_gml_time_period_gml_id xml_buffer, energy_refurbishment_measure{}.energy_refurbishment_measure_energy_date_energy_date_of_event_energy_period_gml_time_period_gml_end_gml_time_instant_gml_related_time{}.gml_time_node_gml_position_xlink_href xml_buffer, energy_refurbishment_measure{}.energy_refurbishment_measure_energy_date_energy_date_of_event_energy_period_gml_time_period_gml_end_gml_time_instant_gml_related_time{}.gml_time_node_gml_position_gml_time_instant xml_xml, energy_refurbishment_measure{}.energy_refurbishment_measure_energy_date_energy_date_of_event_energy_period_gml_time_period_gml_end_gml_time_instant_gml_related_time{}.gml_time_node_gml_position_gml_time_instant_frame xml_buffer, energy_refurbishment_measure{}.energy_refurbishment_measure_energy_date_energy_date_of_event_energy_period_gml_time_period_gml_end_gml_time_instant_gml_related_time{}.gml_time_node_gml_position_gml_time_instant_gml_id xml_buffer, energy_refurbishment_measure{}.energy_refurbishment_measure_energy_date_energy_date_of_event_energy_period_gml_time_period_gml_end_gml_time_instant_gml_related_time{}.gml_time_period xml_xml, energy_refurbishment_measure{}.energy_refurbishment_measure_energy_date_energy_date_of_event_energy_period_gml_time_period_gml_end_gml_time_instant_gml_related_time{}.gml_time_period_frame xml_buffer, energy_refurbishment_measure{}.energy_refurbishment_measure_energy_date_energy_date_of_event_energy_period_gml_time_period_gml_end_gml_time_instant_gml_related_time{}.gml_time_period_gml_id xml_buffer, energy_refurbishment_measure{}.energy_refurbishment_measure_energy_date_energy_date_of_event_energy_period_gml_time_period_gml_end_gml_time_instant_gml_time_position xml_buffer, energy_refurbishment_measure{}.energy_refurbishment_measure_energy_date_energy_date_of_event_energy_period_gml_time_period_gml_end_gml_time_instant_gml_time_position_frame xml_buffer, energy_refurbishment_measure{}.energy_refurbishment_measure_energy_date_energy_date_of_event_energy_period_gml_time_period_gml_end_gml_time_instant_gml_time_position_calendarEraName xml_buffer, energy_refurbishment_measure{}.energy_refurbishment_measure_energy_date_energy_date_of_event_energy_period_gml_time_period_gml_end_gml_time_instant_gml_time_position_indeterminatePosition xml_char(7), energy_refurbishment_measure{}.energy_refurbishment_measure_energy_date_energy_date_of_event_energy_period_gml_time_period_gml_duration xml_buffer, energy_refurbishment_measure{}.energy_refurbishment_measure_energy_date_energy_date_of_event_energy_period_gml_time_period_gml_time_interval xml_real64, energy_refurbishment_measure{}.energy_refurbishment_measure_energy_date_energy_date_of_event_energy_period_gml_time_period_gml_time_interval_unit xml_buffer, energy_refurbishment_measure{}.energy_refurbishment_measure_energy_date_energy_date_of_event_energy_period_gml_time_period_gml_time_interval_radix xml_uint64, energy_refurbishment_measure{}.energy_refurbishment_measure_energy_date_energy_date_of_event_energy_period_gml_time_period_gml_time_interval_factor xml_int64, energy_refurbishment_measure{}.energy_refurbishment_measure_energy_level xml_buffer, energy_refurbishment_measure{}.energy_refurbishment_measure_energy_level_codeSpace xml_buffer, energy_refurbishment_measure{}.energy_refurbishment_measure_energy_description xml_buffer, energy_thermal_zone{}.xlink_href xml_buffer, energy_usage_zone{}.xlink_href xml_buffer,
      energy_volume{}.energy_volume_type_energy_type xml_char(21), energy_volume{}.energy_volume_type_energy_value xml_real64, energy_volume{}.energy_volume_type_energy_value_units xml_buffer
BuildingUnit (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_rooms xml_int32, energy_owner_name xml_buffer, energy_ownership_type xml_buffer, energy_ownership_type_codeSpace xml_buffer, energy_floor_area{}.energy_floor_area_energy_type xml_char(19), energy_floor_area{}.energy_floor_area_energy_value xml_real64, energy_floor_area{}.energy_floor_area_energy_value_units xml_buffer, energy_energy_performance_certification{}.energy_energy_performance_certification_energy_rating xml_buffer, energy_energy_performance_certification{}.energy_energy_performance_certification_energy_name xml_buffer, energy_energy_performance_certification{}.energy_energy_performance_certification_energy_certification_id xml_buffer, energy_occupied_by{}.xlink_href xml_buffer, energy_address{}.xlink_href xml_buffer,
      energy_equipped_with{}.xlink_href xml_buffer
    -> AttributeManager_6
Chiller (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_condensation_type xml_char(18), energy_compressor_type xml_char(35), energy_refrigerant xml_buffer
    -> AttributeManager_20
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
    -> CityModel (writer CITYGML_2)
CityModel (writer CITYGML_2)
    attributes: citygml_target_uri xml_buffer, gml_description xml_buffer, gml_name xml_buffer, citygml_city_object_member{}.xlink_href xml_buffer, citygml_appearance_member{}.xlink_href xml_buffer, gml_feature_member{}.xlink_href xml_buffer
Construction (reader CITYGML_1)
    attributes: citygml_target_uri xml_buffer, citygml_feature_role xml_buffer, citygml_feature_role_attr_name xml_buffer, citygml_feature_role_attr_val xml_buffer, energy_u_value xml_real64, energy_u_value_units xml_buffer, energy_optical_properties_energy_optical_properties_energy_emissivity{}.energy_emissivity_energy_fraction xml_real64, energy_optical_properties_energy_optical_properties_energy_emissivity{}.energy_emissivity_energy_fraction_units xml_buffer, energy_optical_properties_energy_optical_properties_energy_emissivity{}.energy_emissivity_energy_surface xml_char(7), energy_optical_properties_energy_optical_properties_energy_reflectance{}.energy_reflectance_energy_fraction xml_real64, energy_optical_properties_energy_optical_properties_energy_reflectance{}.energy_reflectance_energy_fraction_units xml_buffer, energy_optical_properties_energy_optical_properties_energy_reflectance{}.energy_reflectance_energy_surface xml_char(7), energy_optical_properties_energy_optical_properties_energy_reflectance{}.energy_reflectance_energy_wavelength_range xml_char(8), energy_optical_properties_energy_optical_properties_energy_transmittance{}.energy_transmittance_energy_fraction xml_real64, energy_optical_properties_energy_optical_properties_energy_transmittance{}.energy_transmittance_energy_fraction_units xml_buffer, energy_optical_properties_energy_optical_properties_energy_transmittance{}.energy_transmittance_energy_wavelength_range xml_char(8), energy_optical_properties_energy_optical_properties_energy_glazing_ratio xml_real64, energy_optical_properties_energy_optical_properties_energy_glazing_ratio_units xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_layer{}.xlink_href xml_buffer
    -> AttributeManager_9
AttributeManager_9
    ATTR_TABLE:
      SET_TO citygml_feature_role = gml:featureMember
      SET_TO energy_service_life_energy_service_life_gml_id = FME_CONDITIONAL:DEFAULT_VALUE'_FME_NO_OP_'BOOL_OP;OR;COMPOSITE_TEST;1;TEST @Value(gml_id) = id_construction_iwall_4'id_serviceLife_iWall_4'FME_NUM_CONDITIONS2___
      SET_TO energy_service_life_energy_service_life_energy_start_of_life = FME_CONDITIONAL:DEFAULT_VALUE'_FME_NO_OP_'BOOL_OP;OR;COMPOSITE_TEST;1;TEST @Value(gml_id) = id_construction_iwall_4'2015-03-03'FME_NUM_CONDITIONS2___
      SET_TO energy_service_life_energy_service_life_energy_life_expectancy = FME_CONDITIONAL:DEFAULT_VALUE'_FME_NO_OP_'BOOL_OP;OR;COMPOSITE_TEST;1;TEST @Value(gml_id) = id_construction_iwall_4'15'FME_NUM_CONDITIONS2___
      SET_TO energy_service_life_energy_service_life_energy_life_expectancy_unit = FME_CONDITIONAL:DEFAULT_VALUE'_FME_NO_OP_'BOOL_OP;OR;COMPOSITE_TEST;1;TEST @Value(gml_id) = id_construction_iwall_4'year'FME_NUM_CONDITIONS2___
      SET_TO energy_service_life_energy_service_life_energy_main_maintenance_interval = FME_CONDITIONAL:DEFAULT_VALUE'_FME_NO_OP_'BOOL_OP;OR;COMPOSITE_TEST;1;TEST @Value(gml_id) = id_construction_iwall_4'1'FME_NUM_CONDITIONS2___
      SET_TO energy_service_life_energy_service_life_energy_main_maintenance_interval_unit = FME_CONDITIONAL:DEFAULT_VALUE'_FME_NO_OP_'BOOL_OP;OR;COMPOSITE_TEST;1;TEST @Value(gml_id) = id_construction_iwall_4'year'FME_NUM_CONDITIONS2___
    -> Construction (writer CITYGML_2)
Construction (writer CITYGML_2)
    attributes: citygml_target_uri xml_buffer, citygml_feature_role xml_buffer, citygml_feature_role_attr_name xml_buffer, citygml_feature_role_attr_val xml_buffer, energy_u_value xml_real64, energy_u_value_units xml_buffer, energy_optical_properties_energy_optical_properties_energy_emissivity{}.energy_emissivity_energy_fraction xml_real64, energy_optical_properties_energy_optical_properties_energy_emissivity{}.energy_emissivity_energy_fraction_units xml_buffer, energy_optical_properties_energy_optical_properties_energy_emissivity{}.energy_emissivity_energy_surface xml_char(7), energy_optical_properties_energy_optical_properties_energy_reflectance{}.energy_reflectance_energy_fraction xml_real64, energy_optical_properties_energy_optical_properties_energy_reflectance{}.energy_reflectance_energy_fraction_units xml_buffer, energy_optical_properties_energy_optical_properties_energy_reflectance{}.energy_reflectance_energy_surface xml_char(7), energy_optical_properties_energy_optical_properties_energy_reflectance{}.energy_reflectance_energy_wavelength_range xml_char(8), energy_optical_properties_energy_optical_properties_energy_transmittance{}.energy_transmittance_energy_fraction xml_real64, energy_optical_properties_energy_optical_properties_energy_transmittance{}.energy_transmittance_energy_fraction_units xml_buffer, energy_optical_properties_energy_optical_properties_energy_transmittance{}.energy_transmittance_energy_wavelength_range xml_char(8), energy_optical_properties_energy_optical_properties_energy_glazing_ratio xml_real64, energy_optical_properties_energy_optical_properties_energy_glazing_ratio_units xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_layer{}.xlink_href xml_buffer
DHWFacilities (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_operation_schedule xml_xml, energy_operation_schedule_xlink_href xml_buffer, energy_heat_dissipation_energy_heat_exchange_type_energy_convective_fraction xml_real64, energy_heat_dissipation_energy_heat_exchange_type_energy_convective_fraction_units xml_buffer, energy_heat_dissipation_energy_heat_exchange_type_energy_latent_fraction xml_real64, energy_heat_dissipation_energy_heat_exchange_type_energy_latent_fraction_units xml_buffer, energy_heat_dissipation_energy_heat_exchange_type_energy_radiant_fraction xml_real64, energy_heat_dissipation_energy_heat_exchange_type_energy_radiant_fraction_units xml_buffer, energy_heat_dissipation_energy_heat_exchange_type_energy_total_value xml_real64, energy_heat_dissipation_energy_heat_exchange_type_energy_total_value_units xml_buffer, energy_number_of_baths xml_int32, energy_number_of_showers xml_int32,
      energy_number_of_wash_basins xml_int32, energy_water_storage_volume xml_real64, energy_water_storage_volume_units xml_buffer
    -> DHWFacilities (writer CITYGML_2)
DHWFacilities (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_operation_schedule xml_xml, energy_operation_schedule_xlink_href xml_buffer, energy_heat_dissipation_energy_heat_exchange_type_energy_convective_fraction xml_real64, energy_heat_dissipation_energy_heat_exchange_type_energy_convective_fraction_units xml_buffer, energy_heat_dissipation_energy_heat_exchange_type_energy_latent_fraction xml_real64, energy_heat_dissipation_energy_heat_exchange_type_energy_latent_fraction_units xml_buffer, energy_heat_dissipation_energy_heat_exchange_type_energy_radiant_fraction xml_real64, energy_heat_dissipation_energy_heat_exchange_type_energy_radiant_fraction_units xml_buffer, energy_heat_dissipation_energy_heat_exchange_type_energy_total_value xml_real64, energy_heat_dissipation_energy_heat_exchange_type_energy_total_value_units xml_buffer, energy_number_of_baths xml_int32, energy_number_of_showers xml_int32,
      energy_number_of_wash_basins xml_int32, energy_water_storage_volume xml_real64, energy_water_storage_volume_units xml_buffer
EmitterSystem (reader CITYGML_1)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_emitter_type xml_char(17), energy_installed_power xml_real64, energy_installed_power_units xml_buffer, energy_thermal_exchange_energy_heat_exchange_type_energy_convective_fraction xml_real64, energy_thermal_exchange_energy_heat_exchange_type_energy_convective_fraction_units xml_buffer, energy_thermal_exchange_energy_heat_exchange_type_energy_latent_fraction xml_real64, energy_thermal_exchange_energy_heat_exchange_type_energy_latent_fraction_units xml_buffer, energy_thermal_exchange_energy_heat_exchange_type_energy_radiant_fraction xml_real64, energy_thermal_exchange_energy_heat_exchange_type_energy_radiant_fraction_units xml_buffer, energy_thermal_exchange_energy_heat_exchange_type_energy_total_value xml_real64, energy_thermal_exchange_energy_heat_exchange_type_energy_total_value_units xml_buffer, energy_emitts{}.xlink_href xml_buffer
    -> AttributeManager_29
EnergyFlow (reader CITYGML_1)
    attributes: citygml_target_uri xml_buffer, citygml_feature_role xml_buffer, citygml_feature_role_attr_name xml_buffer, citygml_feature_role_attr_val xml_buffer, gml_description xml_buffer, gml_name xml_buffer, energy_energy_amount xml_xml, energy_energy_amount_xlink_href xml_buffer, energy_energy_carrier_type xml_buffer, energy_energy_carrier_type_codeSpace xml_buffer, energy_is_provided_by{}.xlink_href xml_buffer, energy_is_distributed_by{}.xlink_href xml_buffer, energy_is_emitted_by{}.xlink_href xml_buffer, energy_is_stored_by{}.xlink_href xml_buffer
    -> AttributeFilter
EnergySource (reader CITYGML_1)
    attributes: citygml_target_uri xml_buffer, citygml_feature_role xml_buffer, citygml_feature_role_attr_name xml_buffer, citygml_feature_role_attr_val xml_buffer, gml_description xml_buffer, gml_name xml_buffer, energy_energy_amount xml_xml, energy_energy_amount_xlink_href xml_buffer, energy_energy_carrier_type xml_buffer, energy_energy_carrier_type_codeSpace xml_buffer, energy_is_provided_by{}.xlink_href xml_buffer, energy_is_distributed_by{}.xlink_href xml_buffer, energy_is_emitted_by{}.xlink_href xml_buffer, energy_is_stored_by{}.xlink_href xml_buffer, energy_co2_emission_factor xml_real64, energy_co2_emission_factor_units xml_buffer, energy_energy_density xml_real64, energy_energy_density_units xml_buffer, energy_primary_energy_factor xml_real64, energy_primary_energy_factor_units xml_buffer
    -> AttributeManager_30
Creator_16
    GEOMTYPE = Geometry Object
    NUM = 1
    CREATED -> AttributeManager_23
AttributeManager_23
    ATTR_TABLE:
      SET_TO energy_number_of_devices = 1
      SET_TO gml_id = id_ST_System_1
      SET_TO citygml_feature_role = cityObjectMember
      SET_TO citygml_target_uri = http://www.sig3d.org/citygml/2.0/energy/1.0
      SET_TO citygml_feature_role_attr_name
      SET_TO energy_model = st3000
      SET_TO energy_service_life_xlink_href = #id_serviceLife_Conversion_System_9
      SET_TO gml_description
      SET_TO gml_name
      SET_TO energy_year_of_manufacure = 2005
      SET_TO energy_efficiency_indicator = B
      SET_TO energy_installed_power = 300
      SET_TO energy_installed_power_units = kWh
      SET_TO energy_nominal_efficiency = 0.75
      SET_TO energy_nominal_efficiency_units = ratio
      SET_TO energy_installed_on_boundary_surface_xlink_href = #id_building_1_roofsurface_1
      SET_TO energy_collector_type = flatPlaneCollector
      SET_TO energy_aperture_area = 3
      SET_TO energy_aperture_area_units = m2
      SET_TO energy_eta0 = 0.5
      SET_TO energy_a1 = 0.2
      SET_TO energy_a2 = 0.4
      SET_TO
    -> SolarThermalSystem (writer CITYGML_2)
SolarThermalSystem (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, citygml_level_of_detail{} xml_buffer, energy_installed_on_boundary_surface_xlink_href xml_buffer, energy_installed_on_building_installation_xlink_href xml_buffer, energy_collector_type xml_char(22), energy_aperture_area xml_real64, energy_aperture_area_units xml_buffer, energy_eta0 xml_real64, energy_a1 xml_real64, energy_a2 xml_real64
Creator_17
    GEOMTYPE = Geometry Object
    NUM = 3
    CREATED -> AttributeFilter_2
AttributeFilter_2
    ATTR_NAME = _creation_instance
    ATTR_VALUES = <Empty>,<Missing>,<Null>,<Unfiltered>,1,2
    <UNFILTERED> -> AttributeManager_24
    1 -> AttributeManager_36
    2 -> AttributeManager_37
AttributeManager_24
    ATTR_TABLE:
      SET_TO gml_id = id_system_operation_1
      SET_TO gml_parent_id = id_Boiler_1
      SET_TO citygml_feature_role = has
      SET_TO energy_end_use = domesticHotWater
      SET_TO energy_yearly_global_efficiency = 0.75
    -> SystemOperation (writer CITYGML_2)
AttributeManager_36
    ATTR_TABLE:
      SET_TO gml_id = id_system_operation_2
      SET_TO gml_parent_id = id_Heat_pump_1
      SET_TO citygml_feature_role = has
      SET_TO energy_end_use = domesticHotWater
      SET_TO energy_yearly_global_efficiency = 0.75
      SET_TO energy_operation_time_energy_dual_value_schedule_gml_id = id_dual_value_1
      SET_TO energy_operation_time_energy_dual_value_schedule_energy_usage_hours_per_day = 12
      SET_TO energy_operation_time_energy_dual_value_schedule_energy_usage_days_per_year = 250
      SET_TO energy_operation_time_energy_dual_value_schedule_energy_usage_value = 200
      SET_TO energy_operation_time_energy_dual_value_schedule_energy_usage_value_units = kWh
      SET_TO energy_operation_time_energy_dual_value_schedule_energy_idle_value = 50
      SET_TO energy_operation_time_energy_dual_value_schedule_energy_idle_value_units = kWh
    USER_EXPOSED_ATTRIBUTES = energy_operation_time_energy_dual_value_schedule_gml_id,energy_operation_time_energy_dual_value_schedule_energy_usage_hours_per_day,energy_operation_time_energy_dual_value_schedule_energy_usage_days_per_year,energy_operation_time_energy_dual_value_schedule_energy_usage_value,energy_operation_time_energy_dual_value_schedule_energy_usage_value_units,energy_operation_time_energy_dual_value_schedule_energy_idle_value,energy_operation_time_energy_dual_value_schedule_energy_idle_value_units
    -> SystemOperation (writer CITYGML_2)
AttributeManager_37
    ATTR_TABLE:
      SET_TO gml_id = id_system_operation_3
      SET_TO gml_parent_id = id_Boiler_1
      SET_TO citygml_feature_role = has
      SET_TO energy_end_use = domesticHotWater
      SET_TO energy_yearly_global_efficiency = 0.75
      SET_TO energy_operation_time_energy_time_series_schedule_energy_time_depending_values_xlink_href = #id_nrg_dem_heat_dem_timeseries_1
    USER_EXPOSED_ATTRIBUTES = energy_operation_time_energy_time_series_schedule_energy_time_depending_values_xlink_href
    -> SystemOperation (writer CITYGML_2)
SystemOperation (writer CITYGML_2)
    attributes: citygml_target_uri xml_buffer, citygml_feature_role xml_buffer, citygml_feature_role_attr_name xml_buffer, citygml_feature_role_attr_val xml_buffer, gml_description xml_buffer, gml_name xml_buffer, energy_end_use xml_char(20), energy_operation_time xml_xml, energy_operation_time_xlink_href xml_buffer, energy_yearly_global_efficiency xml_real64
Creator_19
    GEOMTYPE = Geometry Object
    NUM = 1
    CREATED -> AttributeManager_28
AttributeManager_28
    ATTR_TABLE:
      SET_TO gml_id = id_thermal_ditribution_system_1
      SET_TO citygml_feature_role = cityObjectMember
      SET_TO energy_year_of_manufacure = 2020
      SET_TO energy_is_circulation = true
      SET_TO energy_medium = air
      SET_TO energy_nominal_flow = 0.6
      SET_TO energy_nominal_flow_units = ratio
      SET_TO energy_return_temperature = 35
      SET_TO energy_return_temperature_units = Degree Celsius
      SET_TO energy_supply_temperature = 40
      SET_TO energy_supply_temperature_units = Degree Celsius
      SET_TO energy_thermal_losses_factor = 0.2
      SET_TO energy_thermal_losses_factor_units = ratio
    -> ThermalDistributionSystem (writer CITYGML_2)
ThermalDistributionSystem (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_distribution_perimeter xml_char(16), energy_distributes{}.xlink_href xml_buffer, energy_is_circulation xml_boolean, energy_medium xml_char(5), energy_nominal_flow xml_real64, energy_nominal_flow_units xml_buffer, energy_return_temperature xml_real64, energy_return_temperature_units xml_buffer, energy_supply_temperature xml_real64, energy_supply_temperature_units xml_buffer, energy_thermal_losses_factor xml_real64, energy_thermal_losses_factor_units xml_buffer
Creator_18
    GEOMTYPE = Geometry Object
    NUM = 1
    CREATED -> AttributeManager_25
AttributeManager_25
    ATTR_TABLE:
      SET_TO gml_id = id_thermal_storage_system_1
      SET_TO citygml_feature_role = cityObjectMember
      SET_TO energy_number_of_devices = 1
      SET_TO energy_model = TSS500
      SET_TO energy_year_of_manufacure = 2003
      SET_TO energy_preparation_temperature = 50
      SET_TO energy_preparation_temperature_units = Degree Celcius
      SET_TO energy_medium = water
      SET_TO energy_thermal_losses_factor = 0.2
      SET_TO energy_thermal_losses_factor_units = ratio
      SET_TO energy_volume = 1000
      SET_TO energy_volume_units = m3
    -> ThermalStorageSystem (writer CITYGML_2)
ThermalStorageSystem (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_stores{}.xlink_href xml_buffer, energy_preparation_temperature xml_real64, energy_preparation_temperature_units xml_buffer, energy_medium xml_char(5), energy_thermal_losses_factor xml_real64, energy_thermal_losses_factor_units xml_buffer, energy_volume xml_real64, energy_volume_units xml_buffer
Creator_4
    GEOMTYPE = Geometry Object
    NUM = 1
    CREATED -> AttributeManager_8
    CREATED -> AttributeManager_16
AttributeManager_8
    ATTR_TABLE:
      SET_TO gml_id = id_address_BU1
      SET_TO gml_parent_id = id_building_1_buildingUnit_1
      SET_TO citygml_feature_role = address
    -> XMLTemplater [ROOT]
XMLTemplater
    OUTPUT_XML_HEADER = Yes
    RESULT_ATTRIBUTE = citygml_address
    ROOT_QUERY_EXPR:
      <core:xalAddress xmlns:core="http://www.opengis.net/citygml/2.0">
             <xAL:AddressDetails xmlns:xAL="urn:oasis:names:tc:ciq:xsdschema:xAL:2.0">
                 <xAL:Locality Type="Town">
                       <xAL:LocalityName>Exegol</xAL:LocalityName>
                      <xAL:Thoroughfare Type="Street">
                          <xAL:ThoroughfareNumber>32</xAL:ThoroughfareNumber>
                          <xAL:ThoroughfareName>Palace Street</xAL:ThoroughfareName>
                      </xAL:Thoroughfare>
                      <xAL:PostalCode>
                          <xAL:PostalCodeNumber>76131</xAL:PostalCodeNumber>
                      </xAL:PostalCode>
                  </xAL:Locality>
              </xAL:AddressDetails>
      </core:xalAddress>
    VISIBLE_QUERY_VALIDATE = Yes
    -> Address (writer CITYGML_2)
Address (writer CITYGML_2)
    attributes: citygml_target_uri xml_buffer, citygml_feature_role xml_buffer, citygml_feature_role_attr_name xml_buffer, citygml_feature_role_attr_val xml_buffer, gml_description xml_buffer, gml_name xml_buffer, citygml_address xml_xml
AttributeManager_16
    ATTR_TABLE:
      SET_TO energy_number_of_devices = 1
      SET_TO gml_id = id_AirCompressor_1
      SET_TO citygml_feature_role = cityObjectMember
      SET_TO citygml_target_uri = http://www.sig3d.org/citygml/2.0/energy/1.0
      SET_TO citygml_feature_role_attr_name
      SET_TO energy_model = AirCompressor3000
      SET_TO energy_service_life_energy_service_life_gml_id = id_serviceLife_Conversion_System_4
      SET_TO gml_description
      SET_TO gml_name
      SET_TO energy_service_life_energy_service_life_energy_start_of_life = 2020-07-07
      SET_TO energy_service_life_energy_service_life_energy_life_expectancy = 15
      SET_TO energy_service_life_energy_service_life_energy_life_expectancy_unit = year
      SET_TO energy_service_life_energy_service_life_energy_main_maintenance_interval = 2
      SET_TO energy_service_life_energy_service_life_energy_main_maintenance_interval_unit = year
      SET_TO energy_year_of_manufacure = 2005
      SET_TO energy_efficiency_indicator = B
      SET_TO energy_installed_power = 300
      SET_TO energy_installed_power_units = kWh
      SET_TO energy_nominal_efficiency = 0.75
      SET_TO energy_nominal_efficiency_units = ratio
      SET_TO energy_compressor_type = screwCompressor
      SET_TO energy_pressure = 10000
      SET_TO energy_pressure_units = pa
    -> AttributeCreator_6
AttributeCreator_6
    ATTR_TABLE = SET_TO energy_installed_in{0}.xlink_href = #id_building_01
    -> AirCompressor (writer CITYGML_2)
AirCompressor (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_compressor_type xml_char(35), energy_pressure xml_real64, energy_pressure_units xml_buffer
Creator
    GEOMTYPE = Geometry Object
    NUM = 1
    CREATED -> AttributeManager
AttributeManager
    ATTR_TABLE:
      SET_TO energy_number_of_devices = 1
      SET_TO gml_id = id_Boiler_1
      SET_TO citygml_feature_role = cityObjectMember
      SET_TO citygml_target_uri = http://www.sig3d.org/citygml/2.0/energy/1.0
      SET_TO citygml_feature_role_attr_name
      SET_TO energy_model = Superboiler3000
      SET_TO energy_service_life_energy_service_life_gml_id = id_serviceLife_Conversion_System_1
      SET_TO gml_description = Boiler Bathroom 1
      SET_TO gml_name = Boiler 1 Building 1
      SET_TO energy_service_life_energy_service_life_energy_start_of_life = 2020-07-07
      SET_TO energy_service_life_energy_service_life_energy_life_expectancy = 15
      SET_TO energy_service_life_energy_service_life_energy_life_expectancy_unit = year
      SET_TO energy_service_life_energy_service_life_energy_main_maintenance_interval = 2
      SET_TO energy_service_life_energy_service_life_energy_main_maintenance_interval_unit = year
      SET_TO energy_year_of_manufacure = 2005
      SET_TO energy_efficiency_indicator = B
      SET_TO energy_installed_power = 300
      SET_TO energy_installed_power_units = kWh
      SET_TO energy_nominal_efficiency = 0.75
      SET_TO energy_nominal_efficiency_units = ratio
      SET_TO energy_has_condensation = true
    -> AttributeCreator_3
AttributeCreator_3
    ATTR_TABLE = SET_TO energy_installed_in{0}.xlink_href = #id_building_12_usage_zone_1
    -> Boiler (writer CITYGML_2)
Boiler (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_has_condensation xml_boolean
Creator_3
    GEOMTYPE = Geometry Object
    NUM = 1
    CREATED -> AttributeManager_6
    CREATED -> AttributeManager_20
AttributeManager_6
    ATTR_TABLE:
      SET_TO gml_id = id_building_1_buildingUnit_1
      SET_TO gml_parent_id = id_building_1_usage_zone_1
      SET_TO citygml_target_uri = http://www.sig3d.org/citygml/2.0/energy/1.0
      SET_TO citygml_feature_role = contains
      SET_TO gml_description = This is a the BuildingUnit for the UsageZone in Building 1
      SET_TO energy_number_of_rooms = 5
      SET_TO energy_owner_name = Snoke
      SET_TO energy_ownership_type = occupantPrivateOwner
      SET_TO energy_ownership_type_codeSpace = http://hub.geosmartcity.eu/registry/codelist/OwnershipTypeValue/
      REMOVE _creation_instance
    -> AttributeCreator
AttributeCreator
    ATTR_TABLE:
      SET_TO energy_floor_area{0}.energy_floor_area_energy_type = netFloorArea
      SET_TO energy_floor_area{0}.energy_floor_area_energy_value = 275
      SET_TO energy_floor_area{0}.energy_floor_area_energy_value_units = m^2
      SET_TO energy_energy_performance_certification{0}.energy_energy_performance_certification_energy_rating = C
      SET_TO energy_energy_performance_certification{0}.energy_energy_performance_certification_energy_name = CasaClima
      SET_TO energy_energy_performance_certification{0}.energy_energy_performance_certification_energy_certification_id = CC_10247_C
      SET_TO energy_occupied_by{0}.xlink_href = #id_building_1_occupants_1
      SET_TO energy_equipped_with{0}.xlink_href = #id_building_1_facility_4
    -> BuildingUnit (writer CITYGML_2)
BuildingUnit (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_rooms xml_int32, energy_owner_name xml_buffer, energy_ownership_type xml_buffer, energy_ownership_type_codeSpace xml_buffer, energy_floor_area{}.energy_floor_area_energy_type xml_char(19), energy_floor_area{}.energy_floor_area_energy_value xml_real64, energy_floor_area{}.energy_floor_area_energy_value_units xml_buffer, energy_energy_performance_certification{}.energy_energy_performance_certification_energy_rating xml_buffer, energy_energy_performance_certification{}.energy_energy_performance_certification_energy_name xml_buffer, energy_energy_performance_certification{}.energy_energy_performance_certification_energy_certification_id xml_buffer, energy_occupied_by{}.xlink_href xml_buffer, energy_address{}.xlink_href xml_buffer,
      energy_equipped_with{}.xlink_href xml_buffer
AttributeManager_20
    ATTR_TABLE:
      SET_TO energy_number_of_devices = 1
      SET_TO gml_id = id_Chiller_1
      SET_TO citygml_feature_role = cityObjectMember
      SET_TO citygml_target_uri = http://www.sig3d.org/citygml/2.0/energy/1.0
      SET_TO citygml_feature_role_attr_name
      SET_TO energy_model = chiller2000
      SET_TO energy_service_life_energy_service_life_gml_id = id_serviceLife_Conversion_System_7
      SET_TO gml_description
      SET_TO gml_name
      SET_TO energy_service_life_energy_service_life_energy_start_of_life = 2020-07-07
      SET_TO energy_service_life_energy_service_life_energy_life_expectancy = 15
      SET_TO energy_service_life_energy_service_life_energy_life_expectancy_unit = year
      SET_TO energy_service_life_energy_service_life_energy_main_maintenance_interval = 2
      SET_TO energy_service_life_energy_service_life_energy_main_maintenance_interval_unit = year
      SET_TO energy_year_of_manufacure = 2005
      SET_TO energy_efficiency_indicator = B
      SET_TO energy_installed_power = 300
      SET_TO energy_installed_power_units = kWh
      SET_TO energy_nominal_efficiency = 0.75
      SET_TO energy_nominal_efficiency_units = ratio
      SET_TO energy_condensation_type = dryCooling
      SET_TO energy_compressor_type = centrifugalCompressor
      SET_TO energy_refrigerant = water
    -> Chiller (writer CITYGML_2)
Chiller (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_condensation_type xml_char(18), energy_compressor_type xml_char(35), energy_refrigerant xml_buffer
Creator_9
    GEOMTYPE = Geometry Object
    NUM = 1
    CREATED -> AttributeManager_14
AttributeManager_14
    ATTR_TABLE:
      SET_TO energy_number_of_devices = 1
      SET_TO gml_id = id_CombinedHeatPower_1
      SET_TO citygml_feature_role = cityObjectMember
      SET_TO citygml_target_uri = http://www.sig3d.org/citygml/2.0/energy/1.0
      SET_TO citygml_feature_role_attr_name
      SET_TO energy_model = HeatPower2000
      SET_TO energy_service_life_energy_service_life_gml_id = id_serviceLife_Conversion_System_2
      SET_TO gml_description
      SET_TO gml_name = CombinedHeatPower
      SET_TO energy_service_life_energy_service_life_energy_start_of_life = 2020-07-07
      SET_TO energy_service_life_energy_service_life_energy_life_expectancy = 15
      SET_TO energy_service_life_energy_service_life_energy_life_expectancy_unit = year
      SET_TO energy_service_life_energy_service_life_energy_main_maintenance_interval = 2
      SET_TO energy_service_life_energy_service_life_energy_main_maintenance_interval_unit = year
      SET_TO energy_year_of_manufacure = 2005
      SET_TO energy_efficiency_indicator = B
      SET_TO energy_installed_power = 300
      SET_TO energy_installed_power_units = kWh
      SET_TO energy_nominal_efficiency = 0.75
      SET_TO energy_nominal_efficiency_units = ratio
      SET_TO energy_technology_type = technologyXY
      SET_TO energy_thermal_efficiency = 0.7
      SET_TO energy_thermal_efficiency_units = ratio
      SET_TO energy_electrical_efficiency = 0.67
      SET_TO energy_electrical_efficiency_units = ratio
    -> CombinedHeatPower (writer CITYGML_2)
CombinedHeatPower (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_technology_type xml_buffer, energy_thermal_efficiency xml_real64, energy_thermal_efficiency_units xml_buffer, energy_electrical_efficiency xml_real64, energy_electrical_efficiency_units xml_buffer
Creator_8
    GEOMTYPE = Geometry Object
    NUM = 1
    CREATED -> AttributeManager_13
    CREATED -> AttributeManager_29
AttributeManager_13
    ATTR_TABLE:
      SET_TO gml_id = id_electrical_resistance_1
      SET_TO citygml_target_uri = http://www.sig3d.org/citygml/2.0/energy/1.0
      SET_TO citygml_feature_role = cityObjectMember
      SET_TO energy_number_of_devices = 5
      SET_TO energy_model = LightSwitch
      SET_TO energy_year_of_manufacure = 2010
      SET_TO energy_efficiency_indicator = B
    -> AttributeCreator_4
AttributeCreator_4
    ATTR_TABLE = SET_TO energy_installed_in{0}.xlink_href = #id_building_01
    -> ElectricalResistance (writer CITYGML_2)
ElectricalResistance (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer
AttributeManager_29
    ATTR_TABLE:
      SET_TO gml_id = id_emitter_system_1
      SET_TO gml_parent_id = id_energy_flow_1
      SET_TO citygml_target_uri = http://www.sig3d.org/citygml/2.0/energy/1.0
      SET_TO citygml_feature_role = isEmittedBy
      SET_TO energy_number_of_devices = 7
      SET_TO energy_year_of_manufacure = 2017
      SET_TO energy_emitter_type = radiator
      SET_TO energy_installed_power = 10
      SET_TO energy_installed_power_units = KWh
      SET_TO energy_thermal_exchange_energy_heat_exchange_type_energy_convective_fraction = 0.4
      SET_TO energy_thermal_exchange_energy_heat_exchange_type_energy_convective_fraction_units = ratio
      SET_TO energy_thermal_exchange_energy_heat_exchange_type_energy_latent_fraction = 0.2
      SET_TO energy_thermal_exchange_energy_heat_exchange_type_energy_latent_fraction_units = ratio
      SET_TO energy_thermal_exchange_energy_heat_exchange_type_energy_radiant_fraction = 0.3
      SET_TO energy_thermal_exchange_energy_heat_exchange_type_energy_radiant_fraction_units = ratio
      SET_TO energy_thermal_exchange_energy_heat_exchange_type_energy_total_value = 3
      SET_TO energy_thermal_exchange_energy_heat_exchange_type_energy_total_value_units = KWh
    -> AttributeCreator_8
AttributeCreator_8
    ATTR_TABLE = SET_TO energy_emitts{0}.xlink_href = #id_energy_flow_1
    -> EmitterSystem (writer CITYGML_2)
EmitterSystem (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_emitter_type xml_char(17), energy_installed_power xml_real64, energy_installed_power_units xml_buffer, energy_thermal_exchange_energy_heat_exchange_type_energy_convective_fraction xml_real64, energy_thermal_exchange_energy_heat_exchange_type_energy_convective_fraction_units xml_buffer, energy_thermal_exchange_energy_heat_exchange_type_energy_latent_fraction xml_real64, energy_thermal_exchange_energy_heat_exchange_type_energy_latent_fraction_units xml_buffer, energy_thermal_exchange_energy_heat_exchange_type_energy_radiant_fraction xml_real64, energy_thermal_exchange_energy_heat_exchange_type_energy_radiant_fraction_units xml_buffer, energy_thermal_exchange_energy_heat_exchange_type_energy_total_value xml_real64, energy_thermal_exchange_energy_heat_exchange_type_energy_total_value_units xml_buffer, energy_emitts{}.xlink_href xml_buffer
Creator_6
    GEOMTYPE = Geometry Object
    NUM = 1
    CREATED -> AttributeManager_11
    CREATED -> AttributeManager_4
AttributeManager_4
    ATTR_TABLE:
      SET_TO gml_id = id_facilities_1
      SET_TO gml_parent_id = id_building_2_usage_zone_1
      SET_TO citygml_feature_role = equippedWith
      SET_TO energy_heat_dissipation_energy_heat_exchange_type_energy_convective_fraction = 0.2
      SET_TO energy_heat_dissipation_energy_heat_exchange_type_energy_convective_fraction_units = ratio
      SET_TO energy_heat_dissipation_energy_heat_exchange_type_energy_latent_fraction = 0.2
      SET_TO energy_heat_dissipation_energy_heat_exchange_type_energy_latent_fraction_units = ratio
      SET_TO energy_heat_dissipation_energy_heat_exchange_type_energy_radiant_fraction = 0.6
      SET_TO energy_heat_dissipation_energy_heat_exchange_type_energy_radiant_fraction_units = ratio
      SET_TO energy_heat_dissipation_energy_heat_exchange_type_energy_total_value = 50
      SET_TO energy_heat_dissipation_energy_heat_exchange_type_energy_total_value_units = W/m^2
      SET_TO energy_operation_schedule_energy_constant_value_schedule_gml_id = id_constant_value_schedule_1
      SET_TO energy_operation_schedule_energy_constant_value_schedule_energy_average_value = 12
      SET_TO energy_operation_schedule_energy_constant_value_schedule_energy_average_value_units = hours/day
    USER_EXPOSED_ATTRIBUTES = energy_operation_schedule_energy_constant_value_schedule_gml_id,energy_operation_schedule_energy_constant_value_schedule_energy_average_value,energy_operation_schedule_energy_constant_value_schedule_energy_average_value_units
    -> Facilities (writer CITYGML_2)
Facilities (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_operation_schedule xml_xml, energy_operation_schedule_xlink_href xml_buffer, energy_heat_dissipation_energy_heat_exchange_type_energy_convective_fraction xml_real64, energy_heat_dissipation_energy_heat_exchange_type_energy_convective_fraction_units xml_buffer, energy_heat_dissipation_energy_heat_exchange_type_energy_latent_fraction xml_real64, energy_heat_dissipation_energy_heat_exchange_type_energy_latent_fraction_units xml_buffer, energy_heat_dissipation_energy_heat_exchange_type_energy_radiant_fraction xml_real64, energy_heat_dissipation_energy_heat_exchange_type_energy_radiant_fraction_units xml_buffer, energy_heat_dissipation_energy_heat_exchange_type_energy_total_value xml_real64, energy_heat_dissipation_energy_heat_exchange_type_energy_total_value_units xml_buffer
AttributeManager_11
    ATTR_TABLE:
      SET_TO gml_id = id_material_55
      SET_TO gml_parent_id = id_layercomponent_55
      SET_TO citygml_target_uri = http://www.sig3d.org/citygml/2.0/energy/1.0
      SET_TO citygml_feature_role = material
      SET_TO energy_is_ventilated = false
      SET_TO energy_r_value = 0.1
      SET_TO energy_r_value_units = ft2×°F×h/BTU
    -> Gas (writer CITYGML_2)
Gas (writer CITYGML_2)
    attributes: citygml_target_uri xml_buffer, citygml_feature_role xml_buffer, citygml_feature_role_attr_name xml_buffer, citygml_feature_role_attr_val xml_buffer, gml_description xml_buffer, gml_name xml_buffer, energy_image_texture_xlink_href xml_buffer, energy_is_ventilated xml_boolean, energy_r_value xml_real64, energy_r_value_units xml_buffer
Creator_13
    GEOMTYPE = Geometry Object
    NUM = 1
    CREATED -> AttributeManager_19
    CREATED -> AttributeManager_18
AttributeManager_19
    ATTR_TABLE:
      SET_TO energy_number_of_devices = 1
      SET_TO gml_id = id_Heat_Exchanger_1
      SET_TO citygml_feature_role = cityObjectMember
      SET_TO citygml_target_uri = http://www.sig3d.org/citygml/2.0/energy/1.0
      SET_TO citygml_feature_role_attr_name
      SET_TO energy_model = HE3000
      SET_TO energy_service_life_energy_service_life_gml_id = id_serviceLife_Conversion_System_6
      SET_TO gml_description
      SET_TO gml_name
      SET_TO energy_service_life_energy_service_life_energy_start_of_life = 2020-07-07
      SET_TO energy_service_life_energy_service_life_energy_life_expectancy = 15
      SET_TO energy_service_life_energy_service_life_energy_life_expectancy_unit = year
      SET_TO energy_service_life_energy_service_life_energy_main_maintenance_interval = 2
      SET_TO energy_service_life_energy_service_life_energy_main_maintenance_interval_unit = year
      SET_TO energy_year_of_manufacure = 2005
      SET_TO energy_efficiency_indicator = B
      SET_TO energy_installed_power = 300
      SET_TO energy_installed_power_units = kWh
      SET_TO energy_nominal_efficiency = 0.75
      SET_TO energy_nominal_efficiency_units = ratio
      SET_TO energy_network_id = nw_1234
      SET_TO energy_network_node_id = nd_1234
      SET_TO energy_primary_heat_supplier = RWE
    -> HeatExchanger (writer CITYGML_2)
HeatExchanger (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_network_id xml_buffer, energy_network_node_id xml_buffer, energy_primary_heat_supplier xml_buffer
AttributeManager_18
    ATTR_TABLE:
      SET_TO energy_number_of_devices = 1
      SET_TO gml_id = id_Heat_pump_1
      SET_TO citygml_feature_role = cityObjectMember
      SET_TO citygml_target_uri = http://www.sig3d.org/citygml/2.0/energy/1.0
      SET_TO citygml_feature_role_attr_name
      SET_TO energy_model = HP3000
      SET_TO energy_service_life_xlink_href = #id_serviceLife_Conversion_System_5
      SET_TO energy_year_of_manufacure = 2005
      SET_TO energy_efficiency_indicator = B
      SET_TO energy_installed_power = 300
      SET_TO energy_installed_power_units = kWh
      SET_TO energy_nominal_efficiency = 0.75
      SET_TO energy_nominal_efficiency_units = ratio
      SET_TO energy_heat_source = ambientAir
      SET_TO energy_cop_source_temperature = 50
      SET_TO energy_cop_source_temperature_units = Degree Celsius
      SET_TO energy_cop_operation_temperature = 45
      SET_TO energy_cop_operation_temperature_units = Degree Celsius
    -> HeatPump (writer CITYGML_2)
HeatPump (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_heat_source xml_char(25), energy_cop_source_temperature xml_real64, energy_cop_source_temperature_units xml_buffer, energy_cop_operation_temperature xml_real64, energy_cop_operation_temperature_units xml_buffer
Creator_21
    GEOMTYPE = Geometry Object
    NUM = 1
    CREATED -> AttributeManager_33
AttributeManager_33
    ATTR_TABLE:
      SET_TO gml_id = id_image_texture_1
      SET_TO gml_parent_id = id_material_1
      SET_TO citygml_feature_role = imageTexture
      SET_TO energy_url = www.testurl.com
      SET_TO energy_repeat_s = true
      SET_TO energy_repeat_t = true
    -> ImageTexture (writer CITYGML_2)
ImageTexture (writer CITYGML_2)
    attributes: citygml_target_uri xml_buffer, citygml_feature_role xml_buffer, citygml_feature_role_attr_name xml_buffer, citygml_feature_role_attr_val xml_buffer, gml_description xml_buffer, gml_name xml_buffer, energy_url xml_buffer, energy_repeat_s xml_boolean, energy_repeat_t xml_boolean
Creator_5
    GEOMTYPE = Geometry Object
    NUM = 1
    CREATED -> AttributeCreator_2
AttributeCreator_2
    ATTR_TABLE:
      SET_TO gml_id = id_layercomponent_55
      SET_TO gml_parent_id = id_layer_1
      SET_TO citygml_target_uri = http://www.sig3d.org/citygml/2.0/energy/1.0
      SET_TO citygml_feature_role = layerComponent
      SET_TO energy_thickness = 10
      SET_TO energy_thickness_units = mm
      SET_TO gml_name = Layer Component 55
      SET_TO gml_description = Layer Component 55
    -> AttributeManager_10
AttributeManager_10
    ATTR_TABLE:
      SET_TO energy_service_life_energy_service_life_gml_id = FME_CONDITIONAL:DEFAULT_VALUE'_FME_NO_OP_'BOOL_OP;OR;COMPOSITE_TEST;1;TEST @Value(gml_id) = id_layercomponent_1'id_serviceLife_LC1'FME_NUM_CONDITIONS2___
      SET_TO energy_service_life_energy_service_life_energy_start_of_life = FME_CONDITIONAL:DEFAULT_VALUE'_FME_NO_OP_'BOOL_OP;OR;COMPOSITE_TEST;1;TEST @Value(gml_id) = id_layercomponent_1'2002-11-23'FME_NUM_CONDITIONS2___
      SET_TO energy_service_life_energy_service_life_energy_life_expectancy = FME_CONDITIONAL:DEFAULT_VALUE'_FME_NO_OP_'BOOL_OP;OR;COMPOSITE_TEST;1;TEST @Value(gml_id) = id_layercomponent_1'20'FME_NUM_CONDITIONS2___
      SET_TO energy_service_life_energy_service_life_energy_life_expectancy_unit = FME_CONDITIONAL:DEFAULT_VALUE'_FME_NO_OP_'BOOL_OP;OR;COMPOSITE_TEST;1;TEST @Value(gml_id) = id_layercomponent_1'year'FME_NUM_CONDITIONS2___
      SET_TO energy_service_life_energy_service_life_energy_main_maintenance_interval = FME_CONDITIONAL:DEFAULT_VALUE'_FME_NO_OP_'BOOL_OP;OR;COMPOSITE_TEST;1;TEST @Value(gml_id) = id_layercomponent_1'2'FME_NUM_CONDITIONS2___
      SET_TO energy_service_life_energy_service_life_energy_main_maintenance_interval_unit = FME_CONDITIONAL:DEFAULT_VALUE'_FME_NO_OP_'BOOL_OP;OR;COMPOSITE_TEST;1;TEST @Value(gml_id) = id_layercomponent_1'year'FME_NUM_CONDITIONS2___
    -> LayerComponent (writer CITYGML_2)
LayerComponent (writer CITYGML_2)
    attributes: citygml_target_uri xml_buffer, citygml_feature_role xml_buffer, citygml_feature_role_attr_name xml_buffer, citygml_feature_role_attr_val xml_buffer, energy_area_fraction xml_real64, energy_area_fraction_units xml_buffer, energy_thickness xml_real64, energy_thickness_units xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64, energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_material_xlink_href xml_buffer
Creator_10
    GEOMTYPE = Geometry Object
    NUM = 1
    CREATED -> AttributeManager_15
AttributeManager_15
    ATTR_TABLE:
      SET_TO energy_number_of_devices = 1
      SET_TO gml_id = id_Ventilation_1
      SET_TO citygml_feature_role = cityObjectMember
      SET_TO citygml_target_uri = http://www.sig3d.org/citygml/2.0/energy/1.0
      SET_TO citygml_feature_role_attr_name
      SET_TO energy_model = Ventilation3000
      SET_TO energy_service_life_energy_service_life_gml_id = id_serviceLife_Conversion_System_3
      SET_TO gml_description
      SET_TO gml_name
      SET_TO energy_service_life_energy_service_life_energy_start_of_life = 2020-07-07
      SET_TO energy_service_life_energy_service_life_energy_life_expectancy = 15
      SET_TO energy_service_life_energy_service_life_energy_life_expectancy_unit = year
      SET_TO energy_service_life_energy_service_life_energy_main_maintenance_interval = 2
      SET_TO energy_service_life_energy_service_life_energy_main_maintenance_interval_unit = year
      SET_TO energy_year_of_manufacure = 2005
      SET_TO energy_efficiency_indicator = B
      SET_TO energy_installed_power = 300
      SET_TO energy_installed_power_units = kWh
      SET_TO energy_nominal_efficiency = 0.75
      SET_TO energy_nominal_efficiency_units = ratio
      SET_TO energy_has_heat_recovery = true
      SET_TO energy_recuperation_factor = 0.5
      SET_TO energy_recuperation_factor_units = ratio
    -> AttributeCreator_5
AttributeCreator_5
    ATTR_TABLE = SET_TO energy_installed_in{0}.xlink_href = #id_building_01
    -> MechanicalVentilation (writer CITYGML_2)
MechanicalVentilation (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, energy_has_heat_recovery xml_boolean, energy_recuperation_factor xml_real64, energy_recuperation_factor_units xml_buffer
Creator_15
    GEOMTYPE = Geometry Object
    NUM = 1
    CREATED -> AttributeManager_21
AttributeManager_21
    ATTR_TABLE:
      SET_TO energy_number_of_devices = 1
      SET_TO gml_id = id_PV_System_1
      SET_TO citygml_feature_role = cityObjectMember
      SET_TO citygml_target_uri = http://www.sig3d.org/citygml/2.0/energy/1.0
      SET_TO citygml_feature_role_attr_name
      SET_TO energy_model = pv3000
      SET_TO energy_service_life_energy_service_life_gml_id = id_serviceLife_Conversion_System_8
      SET_TO gml_description
      SET_TO gml_name
      SET_TO energy_service_life_energy_service_life_energy_start_of_life = 2020-07-07
      SET_TO energy_service_life_energy_service_life_energy_life_expectancy = 15
      SET_TO energy_service_life_energy_service_life_energy_life_expectancy_unit = year
      SET_TO energy_service_life_energy_service_life_energy_main_maintenance_interval = 2
      SET_TO energy_service_life_energy_service_life_energy_main_maintenance_interval_unit = year
      SET_TO energy_year_of_manufacure = 2005
      SET_TO energy_efficiency_indicator = B
      SET_TO energy_installed_power = 300
      SET_TO energy_installed_power_units = kWh
      SET_TO energy_nominal_efficiency = 0.75
      SET_TO energy_nominal_efficiency_units = ratio
      SET_TO energy_installed_on_boundary_surface_xlink_href = #id_building_1_roofsurface_1
      SET_TO energy_cell_type = monocrystalline
      SET_TO energy_module_area = 5
      SET_TO energy_module_area_units = m2
    -> FeatureMerger [REQUESTOR]
Creator_2
    GEOMTYPE = Geometry Object
    NUM = 1
    CREATED -> AttributeManager_27
    CREATED -> AttributeManager_22
AttributeManager_22
    ATTR_TABLE:
      SET_TO energy_number_of_devices = 1
      SET_TO gml_id = id_PT_System_1
      SET_TO citygml_feature_role = cityObjectMember
      SET_TO citygml_target_uri = http://www.sig3d.org/citygml/2.0/energy/1.0
      SET_TO citygml_feature_role_attr_name
      SET_TO energy_model = pv3000
      SET_TO energy_service_life_energy_service_life_gml_id = id_serviceLife_Conversion_System_9
      SET_TO gml_description
      SET_TO gml_name
      SET_TO energy_service_life_energy_service_life_energy_start_of_life = 2020-07-07
      SET_TO energy_service_life_energy_service_life_energy_life_expectancy = 15
      SET_TO energy_service_life_energy_service_life_energy_life_expectancy_unit = year
      SET_TO energy_service_life_energy_service_life_energy_main_maintenance_interval = 2
      SET_TO energy_service_life_energy_service_life_energy_main_maintenance_interval_unit = year
      SET_TO energy_year_of_manufacure = 2005
      SET_TO energy_efficiency_indicator = B
      SET_TO energy_installed_power = 300
      SET_TO energy_installed_power_units = kWh
      SET_TO energy_nominal_efficiency = 0.75
      SET_TO energy_nominal_efficiency_units = ratio
      SET_TO energy_installed_on_boundary_surface_xlink_href = #id_building_1_roofsurface_1
      SET_TO energy_cell_type = monocrystalline
      SET_TO energy_module_area = 5
      SET_TO energy_module_area_units = m2
      SET_TO energy_collector_type = flatPlaneCollector
      SET_TO energy_aperture_area = 3
      SET_TO energy_aperture_area_units = m2
      SET_TO energy_optical_efficiency = 0.4
      SET_TO energy_optical_efficiency_units = ratio
      SET_TO energy_linear_heat_loss_coefficient = 0.2
      SET_TO energy_quadratic_heat_loss_coefficient = 0.5
    -> PhotovoltaicThermalSystem (writer CITYGML_2)
PhotovoltaicThermalSystem (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, citygml_level_of_detail{} xml_buffer, energy_installed_on_boundary_surface_xlink_href xml_buffer, energy_installed_on_building_installation_xlink_href xml_buffer, energy_cell_type xml_char(15), energy_collector_type xml_char(22), energy_module_area xml_real64, energy_module_area_units xml_buffer, energy_aperture_area xml_real64, energy_aperture_area_units xml_buffer, energy_optical_efficiency xml_real64, energy_optical_efficiency_units xml_buffer, energy_linear_heat_loss_coefficient xml_real64, energy_quadratic_heat_loss_coefficient xml_real64
AttributeManager_27
    ATTR_TABLE:
      SET_TO gml_id = id_power_distribution_system_1
      SET_TO citygml_feature_role = cityObjectMember
      SET_TO energy_number_of_devices = 5
      SET_TO energy_distribution_perimeter = building
      SET_TO energy_current = 300
      SET_TO energy_current_units = ampere
      SET_TO energy_voltage = 300
      SET_TO energy_voltage_units = volt
    -> PowerDistributionSystem (writer CITYGML_2)
PowerDistributionSystem (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_distribution_perimeter xml_char(16), energy_distributes{}.xlink_href xml_buffer, energy_current xml_real64, energy_current_units xml_buffer, energy_voltage xml_real64, energy_voltage_units xml_buffer
Creator_7
    GEOMTYPE = Geometry Object
    NUM = 1
    CREATED -> AttributeManager_12
    CREATED -> AttributeManager_26
AttributeManager_26
    ATTR_TABLE:
      SET_TO gml_id = id_power_storage_system_1
      SET_TO citygml_feature_role = cityObjectMember
      SET_TO energy_number_of_devices = 1
      SET_TO energy_year_of_manufacure = 2010
      SET_TO energy_battery_technology = lithium-ion
      SET_TO energy_power_capacity = 100
      SET_TO energy_power_capacity_units = MWh
    -> PowerStorageSystem (writer CITYGML_2)
PowerStorageSystem (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_stores{}.xlink_href xml_buffer, energy_battery_technology xml_buffer, energy_power_capacity xml_real64, energy_power_capacity_units xml_buffer
AttributeManager_12
    ATTR_TABLE:
      SET_TO gml_id = id_revConstr_1
      SET_TO citygml_target_uri = http://www.sig3d.org/citygml/2.0/energy/1.0
      SET_TO citygml_feature_role = gml:featureMember
      SET_TO energy_base_construction_xlink_href = #id_construction_wall_2
    -> ReverseConstruction (writer CITYGML_2)
ReverseConstruction (writer CITYGML_2)
    attributes: citygml_target_uri xml_buffer, citygml_feature_role xml_buffer, citygml_feature_role_attr_name xml_buffer, citygml_feature_role_attr_val xml_buffer, gml_description xml_buffer, gml_name xml_buffer, energy_base_construction_xlink_href xml_buffer
Creator_12
    GEOMTYPE = Geometry Object
    NUM = 1
    CREATED -> AttributeManager_17
AttributeManager_17
    ATTR_TABLE:
      SET_TO energy_number_of_devices = 1
      SET_TO gml_id = id_Generic_Conversion_System_1
      SET_TO citygml_feature_role = cityObjectMember
      SET_TO citygml_target_uri = http://www.sig3d.org/citygml/2.0/energy/1.0
      SET_TO citygml_feature_role_attr_name
      SET_TO energy_model = ConversionSystem3000
      SET_TO energy_service_life_energy_service_life_gml_id = id_serviceLife_Conversion_System_5
      SET_TO gml_description
      SET_TO gml_name
      SET_TO energy_service_life_energy_service_life_energy_start_of_life = 2020-07-07
      SET_TO energy_service_life_energy_service_life_energy_life_expectancy = 15
      SET_TO energy_service_life_energy_service_life_energy_life_expectancy_unit = year
      SET_TO energy_service_life_energy_service_life_energy_main_maintenance_interval = 2
      SET_TO energy_service_life_energy_service_life_energy_main_maintenance_interval_unit = year
      SET_TO energy_year_of_manufacure = 2005
      SET_TO energy_efficiency_indicator = B
      SET_TO energy_installed_power = 300
      SET_TO energy_installed_power_units = kWh
      SET_TO energy_nominal_efficiency = 0.75
      SET_TO energy_nominal_efficiency_units = ratio
    -> GenericConversionSystem (writer CITYGML_2)
GenericConversionSystem (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer
Creator_22
    GEOMTYPE = Geometry Object
    NUM = 3
    CREATED -> AttributeFilter
AttributeFilter
    ATTR_NAME = _creation_instance
    ATTR_VALUES = <Empty>,<Missing>,<Null>,<Unfiltered>,1,2
    <UNFILTERED> -> AttributeManager_3
    1 -> AttributeManager_34
    2 -> AttributeManager_35
AttributeManager_3
    ATTR_TABLE:
      SET_TO gml_id = id_energy_flow_1
      SET_TO gml_parent_id = id_CombinedHeatPower_1
      SET_TO citygml_target_uri = http://www.sig3d.org/citygml/2.0/energy/1.0
      SET_TO citygml_feature_role = provides
      SET_TO gml_description = hot water energy flow
      SET_TO energy_energy_amount_xlink_href = #id_timeseries_92
      SET_TO energy_energy_carrier_type = hotWater
      SET_TO energy_energy_carrier_type_codeSpace = http://hub.geosmartcity.eu/registry/codelist/EnergyCarrierTypeValue
      SET_TO energy_is_provided_by{}.xlink_href
      SET_TO energy_is_distributed_by{}.xlink_href
      SET_TO energy_is_emitted_by{}.xlink_href
      SET_TO energy_is_stored_by{}.xlink_href
    -> AttributeCreator_12
AttributeCreator_12
    ATTR_TABLE:
      SET_TO energy_is_stored_by{0}.xlink_href = #id_power_storage_system_1
      SET_TO energy_is_emitted_by{0}.xlink_href = #id_emitter_system_1
      SET_TO energy_is_distributed_by{0}.xlink_href = #id_power_distribution_system_1
      SET_TO energy_is_provided_by{0}.xlink_href = #id_CombinedHeatPower_1
    -> EnergyFlow (writer CITYGML_2)
AttributeManager_34
    ATTR_TABLE:
      SET_TO gml_id = id_energy_flow_2
      SET_TO gml_parent_id = id_thermal_storage_system_1
      SET_TO citygml_target_uri = http://www.sig3d.org/citygml/2.0/energy/1.0
      SET_TO citygml_feature_role = stores
      SET_TO energy_energy_carrier_type = hotWater
      SET_TO energy_is_stored_by{}.xlink_href = #id_thermal_storage_system_1
      SET_TO energy_energy_amount_energy_irregular_time_series_file_gml_id = id_irregularTimeseries_File_1
      SET_TO energy_energy_amount_energy_irregular_time_series_file_energy_variable_properties_energy_time_values_properties_energy_acquisition_method = simulation
      SET_TO energy_energy_amount_energy_irregular_time_series_file_energy_variable_properties_energy_time_values_properties_energy_interpolation_type = succeedingTotal
      SET_TO energy_energy_amount_energy_irregular_time_series_file_energy_variable_properties_energy_time_values_properties_energy_quality_description = sufficient
      SET_TO energy_energy_amount_energy_irregular_time_series_file_energy_variable_properties_energy_time_values_properties_energy_source = renewable
      SET_TO energy_energy_amount_energy_irregular_time_series_file_energy_variable_properties_energy_time_values_properties_energy_thematic_description = energy flow
      SET_TO energy_energy_amount_energy_irregular_time_series_file_energy_uom_units = kWh
      SET_TO energy_energy_amount_energy_irregular_time_series_file_energy_file = www.anyURI.com
      SET_TO energy_energy_amount_energy_irregular_time_series_file_energy_number_of_header_lines = 1
      SET_TO energy_energy_amount_energy_irregular_time_series_file_energy_field_separator = ,
      SET_TO energy_energy_amount_energy_irregular_time_series_file_energy_record_separator = \n
      SET_TO energy_energy_amount_energy_irregular_time_series_file_energy_decimal_symbol = .
      SET_TO energy_energy_amount_energy_irregular_time_series_file_energy_time_column_number = 1
      SET_TO energy_energy_amount_energy_irregular_time_series_file_energy_value_column_number = 2
    USER_EXPOSED_ATTRIBUTES = energy_energy_amount_energy_irregular_time_series_file_gml_id,energy_energy_amount_energy_irregular_time_series_file_energy_variable_properties_energy_time_values_properties_energy_acquisition_method,energy_energy_amount_energy_irregular_time_series_file_energy_variable_properties_energy_time_values_properties_energy_interpolation_type,energy_energy_amount_energy_irregular_time_series_file_energy_variable_properties_energy_time_values_properties_energy_quality_description,energy_energy_amount_energy_irregular_time_series_file_energy_variable_properties_energy_time_values_properties_energy_source,energy_energy_amount_energy_irregular_time_series_file_energy_variable_properties_energy_time_values_properties_energy_thematic_description,energy_energy_amount_energy_irregular_time_series_file_energy_uom_units,energy_energy_amount_energy_irregular_time_series_file_energy_file,energy_energy_amount_energy_irregular_time_series_file_energy_number_of_header_lines,energy_energy_amount_energy_irregular_time_series_file_energy_field_separator,energy_energy_amount_energy_irregular_time_series_file_energy_record_separator,energy_energy_amount_energy_irregular_time_series_file_energy_decimal_symbol,energy_energy_amount_energy_irregular_time_series_file_energy_time_column_number,energy_energy_amount_energy_irregular_time_series_file_energy_value_column_number
    -> AttributeCreator_11
AttributeCreator_11
    ATTR_TABLE = SET_TO energy_is_stored_by{0}.xlink_href = #id_thermal_storage_system_1
    -> EnergyFlow (writer CITYGML_2)
AttributeManager_35
    ATTR_TABLE:
      SET_TO gml_id = id_energy_flow_3
      SET_TO gml_parent_id = id_power_distribution_system_1
      SET_TO citygml_target_uri = http://www.sig3d.org/citygml/2.0/energy/1.0
      SET_TO citygml_feature_role = distributes
      SET_TO energy_energy_carrier_type = naturalGas
      SET_TO energy_energy_amount_energy_regular_time_series_file_gml_id = id_regular_timeseries_file_1
      SET_TO energy_energy_amount_energy_regular_time_series_file_energy_variable_properties_energy_time_values_properties_energy_acquisition_method = measurement
      SET_TO energy_energy_amount_energy_regular_time_series_file_energy_variable_properties_energy_time_values_properties_energy_interpolation_type = continuous
      SET_TO energy_energy_amount_energy_regular_time_series_file_energy_variable_properties_energy_time_values_properties_energy_quality_description = sufficient
      SET_TO energy_energy_amount_energy_regular_time_series_file_energy_variable_properties_energy_time_values_properties_energy_source = own measurements
      SET_TO energy_energy_amount_energy_regular_time_series_file_energy_variable_properties_energy_time_values_properties_energy_thematic_description = Energy flow anergy amount
      SET_TO energy_energy_amount_energy_regular_time_series_file_energy_uom_units = kWh
      SET_TO energy_energy_amount_energy_regular_time_series_file_energy_file = www.dummyfile.com
      SET_TO energy_energy_amount_energy_regular_time_series_file_energy_temporal_extent_gml_time_period_gml_begin_position = 2017-01-01
      SET_TO energy_energy_amount_energy_regular_time_series_file_energy_temporal_extent_gml_time_period_gml_end_position = 2017-12-31
      SET_TO energy_energy_amount_energy_regular_time_series_file_energy_temporal_extent_gml_time_period_gml_duration = P1Y0M0D
      SET_TO energy_energy_amount_energy_regular_time_series_file_energy_time_interval = 0.083
      SET_TO energy_energy_amount_energy_regular_time_series_file_energy_time_interval_unit = year
      SET_TO energy_energy_amount_energy_regular_time_series_file_energy_number_of_header_lines = 0
      SET_TO energy_energy_amount_energy_regular_time_series_file_energy_field_separator = ,
      SET_TO energy_energy_amount_energy_regular_time_series_file_energy_record_separator = \n
      SET_TO energy_energy_amount_energy_regular_time_series_file_energy_decimal_symbol = .
      SET_TO energy_energy_amount_energy_regular_time_series_file_energy_value_column_number = 1
    USER_EXPOSED_ATTRIBUTES = energy_energy_amount_energy_regular_time_series_file_gml_id,energy_energy_amount_energy_irregular_time_series_file_energy_variable_properties_energy_time_values_properties_energy_quality_description,energy_energy_amount_energy_irregular_time_series_file_energy_variable_properties_energy_time_values_properties_energy_acquisition_method,energy_energy_amount_energy_irregular_time_series_file_energy_variable_properties_energy_time_values_properties_energy_source,energy_energy_amount_energy_irregular_time_series_file_energy_variable_properties_energy_time_values_properties_energy_interpolation_type,energy_energy_amount_energy_irregular_time_series_file_energy_variable_properties_energy_time_values_properties_energy_thematic_description,energy_energy_amount_energy_regular_time_series_file_energy_variable_properties_energy_time_values_properties_energy_acquisition_method,energy_energy_amount_energy_regular_time_series_file_energy_variable_properties_energy_time_values_properties_energy_interpolation_type,energy_energy_amount_energy_regular_time_series_file_energy_variable_properties_energy_time_values_properties_energy_quality_description,energy_energy_amount_energy_regular_time_series_file_energy_variable_properties_energy_time_values_properties_energy_source,energy_energy_amount_energy_regular_time_series_file_energy_variable_properties_energy_time_values_properties_energy_thematic_description,energy_energy_amount_energy_regular_time_series_file_energy_uom_units,energy_energy_amount_energy_regular_time_series_file_energy_file,energy_energy_amount_energy_regular_time_series_file_energy_temporal_extent_gml_time_period_gml_begin_position,energy_energy_amount_energy_regular_time_series_file_energy_temporal_extent_gml_time_period_gml_end_position,energy_energy_amount_energy_regular_time_series_file_energy_temporal_extent_gml_time_period_gml_duration,energy_energy_amount_energy_regular_time_series_file_energy_time_interval,energy_energy_amount_energy_regular_time_series_file_energy_time_interval_unit,energy_energy_amount_energy_regular_time_series_file_energy_number_of_header_lines,energy_energy_amount_energy_regular_time_series_file_energy_field_separator,energy_energy_amount_energy_regular_time_series_file_energy_record_separator,energy_energy_amount_energy_regular_time_series_file_energy_decimal_symbol,energy_energy_amount_energy_regular_time_series_file_energy_value_column_number
    -> AttributeCreator_13
AttributeCreator_13
    ATTR_TABLE:
      SET_TO energy_is_stored_by{0}.xlink_href = #id_power_storage_system_1
      SET_TO energy_is_emitted_by{0}.xlink_href = #id_emitter_system_1
      SET_TO energy_is_distributed_by{0}.xlink_href = #id_power_distribution_system_1
      SET_TO energy_is_provided_by{0}.xlink_href = #id_CombinedHeatPower_1
    -> EnergyFlow (writer CITYGML_2)
EnergyFlow (writer CITYGML_2)
    attributes: citygml_target_uri xml_buffer, citygml_feature_role xml_buffer, citygml_feature_role_attr_name xml_buffer, citygml_feature_role_attr_val xml_buffer, gml_description xml_buffer, gml_name xml_buffer, energy_energy_amount xml_xml, energy_energy_amount_xlink_href xml_buffer, energy_energy_carrier_type xml_buffer, energy_energy_carrier_type_codeSpace xml_buffer, energy_is_provided_by{}.xlink_href xml_buffer, energy_is_distributed_by{}.xlink_href xml_buffer, energy_is_emitted_by{}.xlink_href xml_buffer, energy_is_stored_by{}.xlink_href xml_buffer
Creator_11
    GEOMTYPE = Geometry Object
    NUM = 1
    CREATED -> AttributeManager_30
AttributeManager_30
    ATTR_TABLE:
      SET_TO gml_id = id_energy_source_1
      SET_TO gml_parent_id
      SET_TO citygml_target_uri = http://www.sig3d.org/citygml/2.0/energy/1.0
      SET_TO citygml_feature_role = gml:featureMember
      SET_TO energy_energy_amount_xlink_href = #id_timeseries_92
      SET_TO energy_co2_emission_factor = 40
      SET_TO energy_co2_emission_factor_units = uom
      SET_TO energy_energy_density = 3000
      SET_TO energy_energy_density_units = J/kg
      SET_TO energy_primary_energy_factor = 1
      SET_TO energy_primary_energy_factor_units = uom
    -> EnergySource (writer CITYGML_2)
EnergySource (writer CITYGML_2)
    attributes: citygml_target_uri xml_buffer, citygml_feature_role xml_buffer, citygml_feature_role_attr_name xml_buffer, citygml_feature_role_attr_val xml_buffer, gml_description xml_buffer, gml_name xml_buffer, energy_energy_amount xml_xml, energy_energy_amount_xlink_href xml_buffer, energy_energy_carrier_type xml_buffer, energy_energy_carrier_type_codeSpace xml_buffer, energy_is_provided_by{}.xlink_href xml_buffer, energy_is_distributed_by{}.xlink_href xml_buffer, energy_is_emitted_by{}.xlink_href xml_buffer, energy_is_stored_by{}.xlink_href xml_buffer, energy_co2_emission_factor xml_real64, energy_co2_emission_factor_units xml_buffer, energy_energy_density xml_real64, energy_energy_density_units xml_buffer, energy_primary_energy_factor xml_real64, energy_primary_energy_factor_units xml_buffer
PhotovoltaicSystem (writer CITYGML_2)
    attributes: citygml_target_uri xml_buffer, citygml_feature_role xml_buffer, citygml_feature_role_attr_name xml_buffer, citygml_feature_role_attr_val xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, energy_demands{}.xlink_href xml_buffer, energy_weather_data{} xml_xml, energy_weather_data{}.xlink_href xml_buffer, energy_number_of_devices xml_int32, energy_model xml_buffer, energy_service_life_xlink_href xml_buffer, energy_service_life_energy_service_life_gml_id xml_buffer, gml_description xml_buffer, gml_name xml_buffer, energy_service_life_energy_service_life_energy_start_of_life xml_buffer, energy_service_life_energy_service_life_energy_start_of_life_frame xml_buffer, energy_service_life_energy_service_life_energy_start_of_life_calendarEraName xml_buffer, energy_service_life_energy_service_life_energy_start_of_life_indeterminatePosition xml_char(7), energy_service_life_energy_service_life_energy_life_expectancy xml_real64, energy_service_life_energy_service_life_energy_life_expectancy_unit xml_buffer, energy_service_life_energy_service_life_energy_life_expectancy_radix xml_uint64, energy_service_life_energy_service_life_energy_life_expectancy_factor xml_int64,
      energy_service_life_energy_service_life_energy_main_maintenance_interval xml_real64, energy_service_life_energy_service_life_energy_main_maintenance_interval_unit xml_buffer, energy_service_life_energy_service_life_energy_main_maintenance_interval_radix xml_uint64, energy_service_life_energy_service_life_energy_main_maintenance_interval_factor xml_int64, energy_year_of_manufacure xml_buffer, energy_installed_in{}.xlink_href xml_buffer, energy_efficiency_indicator xml_buffer, energy_installed_power xml_real64, energy_installed_power_units xml_buffer, energy_nominal_efficiency xml_real64, energy_nominal_efficiency_units xml_buffer, energy_has{}.xlink_href xml_buffer, energy_provides{}.xlink_href xml_buffer, citygml_level_of_detail{} xml_buffer, energy_installed_on_boundary_surface_xlink_href xml_buffer, energy_installed_on_building_installation_xlink_href xml_buffer, energy_cell_type xml_char(15), energy_module_area xml_real64, energy_module_area_units xml_buffer

Bookmark: IrregularTimeseries
AttributeManager_31
    ATTR_TABLE:
      RENAME_SET_VALUE energy_energy_amount_energy_regular_time_series_energy_variable_properties_energy_time_values_properties_energy_acquisition_method > energy_energy_amount_energy_irregular_time_series_energy_variable_properties_energy_time_values_properties_energy_acquisition_method
      RENAME_SET_VALUE energy_energy_amount_energy_regular_time_series_energy_variable_properties_energy_time_values_properties_energy_interpolation_type > energy_energy_amount_energy_irregular_time_series_energy_variable_properties_energy_time_values_properties_energy_interpolation_type
      RENAME_SET_VALUE energy_energy_amount_energy_regular_time_series_energy_variable_properties_energy_time_values_properties_energy_quality_description > energy_energy_amount_energy_irregular_time_series_energy_variable_properties_energy_time_values_properties_energy_quality_description
      RENAME_SET_VALUE energy_energy_amount_energy_regular_time_series_energy_variable_properties_energy_time_values_properties_energy_source > energy_energy_amount_energy_irregular_time_series_energy_variable_properties_energy_time_values_properties_energy_source
      RENAME_SET_VALUE energy_energy_amount_energy_regular_time_series_energy_variable_properties_energy_time_values_properties_energy_thematic_description > energy_energy_amount_energy_irregular_time_series_energy_variable_properties_energy_time_values_properties_energy_thematic_description = Thematic description text
      RENAME_SET_VALUE energy_energy_amount_energy_regular_time_series_gml_id > energy_energy_amount_energy_irregular_time_series_gml_id
      REMOVE energy_energy_amount_energy_regular_time_series_energy_temporal_extent_gml_time_period_gml_begin_position
      REMOVE energy_energy_amount_energy_regular_time_series_energy_temporal_extent_gml_time_period_gml_end_position
      REMOVE energy_energy_amount_energy_regular_time_series_energy_temporal_extent_gml_time_period_gml_duration
      REMOVE energy_energy_amount_energy_regular_time_series_energy_time_interval
      REMOVE energy_energy_amount_energy_regular_time_series_energy_time_interval_unit
      REMOVE energy_energy_amount_energy_regular_time_series_energy_values
      REMOVE energy_energy_amount_energy_regular_time_series_energy_values_units
      SET_TO energy_energy_amount_energy_irregular_time_series_energy_uom_units = kWh/month
    USER_EXPOSED_ATTRIBUTES = energy_energy_amount_energy_regular_time_series_energy_variable_properties_energy_time_values_properties_energy_acquisition_method,energy_energy_amount_energy_regular_time_series_energy_variable_properties_energy_time_values_properties_energy_interpolation_type,energy_energy_amount_energy_regular_time_series_energy_variable_properties_energy_time_values_properties_energy_quality_description,energy_energy_amount_energy_regular_time_series_energy_variable_properties_energy_time_values_properties_energy_source,energy_energy_amount_energy_regular_time_series_energy_variable_properties_energy_time_values_properties_energy_thematic_description,energy_energy_amount_energy_regular_time_series_gml_id,energy_energy_amount_energy_regular_time_series_energy_temporal_extent_gml_time_period_gml_begin_position,energy_energy_amount_energy_regular_time_series_energy_temporal_extent_gml_time_period_gml_end_position,energy_energy_amount_energy_regular_time_series_energy_temporal_extent_gml_time_period_gml_duration,energy_energy_amount_energy_regular_time_series_energy_time_interval,energy_energy_amount_energy_regular_time_series_energy_time_interval_unit,energy_energy_amount_energy_regular_time_series_energy_values,energy_energy_amount_energy_regular_time_series_energy_values_units,energy_energy_amount_energy_irregular_time_series_energy_uom,energy_energy_amount_energy_irregular_time_series_energy_uom_uri,energy_energy_amount_energy_irregular_time_series_energy_uom_units
    -> AttributeCreator_9
AttributeCreator_9
    ATTR_TABLE:
      SET_TO energy_energy_amount_energy_irregular_time_series_energy_contains{0}.energy_measurement_point_energy_time = 2017-01-01
      SET_TO energy_energy_amount_energy_irregular_time_series_energy_contains{0}.energy_measurement_point_energy_value = 200
      SET_TO energy_energy_amount_energy_irregular_time_series_energy_contains{1}.energy_measurement_point_energy_time = 2017-02-01
      SET_TO energy_energy_amount_energy_irregular_time_series_energy_contains{1}.energy_measurement_point_energy_value = 180
    -> EnergyDemand (writer CITYGML_2)

Bookmark: create geometry for pv system
Creator_20
    GEOM = <?xml version="1.0" encoding="US_ASCII" standalone="no" ?><geometry><polygon><line><coord x="0" y="0"/><coord x="0" y="1"/><coord x="1" y="1"/><coord x="1" y="0"/><coord x="0" y="0"/></line></polygon></geometry>
    GEOMTYPE = Geometry Object
    NUM = 1
    CREATED -> FaceReplacer
FaceReplacer
    ANGULAR_TOLERANCE_CHOICE = Automatic
    THICKNESS_TOLERANCE_CHOICE = Automatic
    -> Aggregator
Aggregator
    ACCUM_ATTRS_NAME = Drop Incoming Attributes
    AGGREGATE_TYPE = Homogeneous Collection (If Possible)
    MODE = Geometry - Assemble One Level
    SEP = ,
    AGGREGATE -> AttributeCreator_7
AttributeCreator_7
    ATTR_TABLE:
      SET_TO citygml_lod_name = surfaceGeometry
      SET_TO gml_id = id_pvpanel
    -> GeometryPropertySetter
GeometryPropertySetter
    GQUERY:
      for $geom in //geometry
      where $geom/@fme_geometry_type = 'IFMEMultiSurface'
      return number($geom/@fme_id)
    OVERWRITE_CHOICE = Yes
    REMOVE_ATTRIBUTE = No
    SETTYPE_PARAM = Traits From Attributes
    SRC_ATTRS = citygml_lod_name gml_id
    SET -> FeatureMerger [SUPPLIER]
FeatureMerger
    JOIN_KEYS = 1 1 AUTO
    MERGE_TYPE = Geometry
    PROCESS_DUPS = NO
    REJECT_NULL_MISSING_KEYS = No
    SUPPLIERS_FIRST = No
    MERGED -> PhotovoltaicSystem (writer CITYGML_2)
